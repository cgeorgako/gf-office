;;; ======================================================================
;;; DGM.lsp - Εργαλεία σύνταξης Διαγραμμάτων Γεωμετρικών Μεταβολών (ΔΓΜ)
;;; για ProgeCAD / IntelliCAD (AutoLISP)
;;;
;;; Εντολές:
;;;   DGML     - Δημιουργία όλων των τυποποιημένων layers ΔΓΜ
;;;   DGMK     - Αρίθμηση κορυφών polyline (σημάδια σε layer "σημείο_...")
;;;   DGMP     - Πίνακας συντεταγμένων κορυφών (Σημείο | Χ | Y | Αποστάσεις)
;;;   DGME     - Πίνακας αρχικών και τελικών εμβαδών επηρεαζόμενων γεωτεμαχίων
;;;   DGMT     - Πίνακας για τη διόρθωση των γεωτεμαχίων (ΤΜΗΜΑ|ΕΜΒΑΔΟΝ|ΑΠΟ|ΣΕ)
;;;   DGMA     - Χαρακτηρισμός τμήματος (ΤΜΗΜΑ Α1/Δ1) και μεταφορά σε AREA_A/AREA_D
;;;   DGMKAEK  - Τοποθέτηση κειμένου ΚΑΕΚ με έλεγχο μορφής
;;;   DGMC     - Έλεγχοι ορθότητας πριν την υποβολή (layers, κλειστότητα κ.λπ.)
;;;   DGMHELP  - Λίστα εντολών
;;;
;;; Σημείωση: Το αρχείο διανομής DGM.lsp είναι κωδικοποιημένο σε Windows-1253
;;; (ελληνικά Windows) ώστε τα ελληνικά να εμφανίζονται σωστά στο ProgeCAD.
;;; ======================================================================

;;; ------------------- Καθολικές ρυθμίσεις / layers ---------------------

(setq dgm:*layers*
 '(("PST_KAEK"              16)
   ("PST"                    7)
   ("TOPO_PROP"             30)
   ("TOPO_PROP_NEW"        224)
   ("DGM_PROP_FINAL"         4)
   ("BOUND_IMPL"            42)
   ("BOUND_UNIMPL"          61)
   ("DBOUND_RYM"            80)
   ("DBOUND_AIG"             1)
   ("DBOUND_PRL"             2)
   ("DBOUND_PAIG"          152)
   ("DBOUND_REM"           141)
   ("DBOUND_APAL"           84)
   ("DBOUND_PROP"            7)
   ("ROAD"                   2)
   ("OT"                    80)
   ("BLD"                  163)
   ("VST"                  233)
   ("EAS"                  233)
   ("MINE"                 157)
   ("LINE_XM"                1)
   ("LINE_XM_VST"            1)
   ("VST_FINAL"              4)
   ("EAS_FINAL"              4)
   ("MINE_FINAL"             4)
   ("AREA_A"                 6)
   ("AREA_D"                 4)
   ("OBJ"                    3)
   ("AREA_A-labels"          6)
   ("AREA_D-labels"          4)
   ("AREA_A-hatch"           3)
   ("AREA_D-hatch"          10)
   ("σημείο_TOPO_PROP"       5)
   ("σημείο_PST_KAEK"       16)
   ("σημείο_DGM_PROP_FINAL"  4)
   ("σημείο_AREAS"           3)
   ("pinakas_sintetagmenon"  7)
   ("Bohthitikesgrammes"     8)
   ("Ktiriaomora"          252 35)
   ("Mandra"                 7 20)
   ("Syrma"                251 20)
  ))

(if (null dgm:*h*)   (setq dgm:*h* 0.5))    ; προεπιλεγμένο ύψος κειμένου
(if (null dgm:*num*) (setq dgm:*num* 0))    ; τρέχων μετρητής αρίθμησης κορυφών
(setq dgm:*numoff* 0.6)  ; μετατόπιση κειμένου αρίθμησης από την κορυφή (x ύψους)

;;; ------------------------- Βοηθητικές: σχεδίαση -----------------------

;; Δημιουργία layer (χρώμα, προεπιλεγμένο πάχος γραμμής).
(defun dgm:layer (name color)
  (if (not (tblsearch "LAYER" name))
    (entmake (list '(0 . "LAYER")
                   '(100 . "AcDbSymbolTableRecord")
                   '(100 . "AcDbLayerTableRecord")
                   (cons 2 name)
                   '(70 . 0)
                   (cons 62 color)
                   '(6 . "Continuous")
                   '(370 . -3))))
  name)

;; Δημιουργία layer με ρητό πάχος γραμμής σε 1/100 mm (π.χ. 35 = 0.35mm).
(defun dgm:layer-lw (name color lw)
  (if (not (tblsearch "LAYER" name))
    (entmake (list '(0 . "LAYER")
                   '(100 . "AcDbSymbolTableRecord")
                   '(100 . "AcDbLayerTableRecord")
                   (cons 2 name)
                   '(70 . 0)
                   (cons 62 color)
                   '(6 . "Continuous")
                   (cons 370 lw))))
  name)

(defun dgm:layer-std (name / a)
  (setq a (assoc name dgm:*layers*))
  (if (and a (caddr a))
    (dgm:layer-lw name (cadr a) (caddr a))
    (dgm:layer name (if a (cadr a) 7))))

(defun dgm:text (pt h str lay)
  (entmake (list '(0 . "TEXT") (cons 8 lay)
                 (cons 10 (list (car pt) (cadr pt) 0.0))
                 (cons 40 h) (cons 1 str) '(50 . 0.0))))

(defun dgm:textc (pt h str lay)
  (entmake (list '(0 . "TEXT") (cons 8 lay)
                 (cons 10 (list (car pt) (cadr pt) 0.0))
                 (cons 11 (list (car pt) (cadr pt) 0.0))
                 (cons 40 h) (cons 1 str) '(50 . 0.0)
                 '(72 . 1) '(73 . 2))))

;; Κεντραρισμένο κείμενο με γωνία περιστροφής ang (σε rad)
(defun dgm:textcr (pt h str lay ang)
  (entmake (list '(0 . "TEXT") (cons 8 lay)
                 (cons 10 (list (car pt) (cadr pt) 0.0))
                 (cons 11 (list (car pt) (cadr pt) 0.0))
                 (cons 40 h) (cons 1 str) (cons 50 ang)
                 '(72 . 1) '(73 . 2))))

(defun dgm:line (p1 p2 lay)
  (entmake (list '(0 . "LINE") (cons 8 lay)
                 (cons 10 (list (car p1) (cadr p1) 0.0))
                 (cons 11 (list (car p2) (cadr p2) 0.0)))))

(defun dgm:rect (x1 y1 x2 y2 lay)
  (dgm:line (list x1 y1) (list x2 y1) lay)
  (dgm:line (list x2 y1) (list x2 y2) lay)
  (dgm:line (list x2 y2) (list x1 y2) lay)
  (dgm:line (list x1 y2) (list x1 y1) lay))

(defun dgm:point (pt lay)
  (entmake (list '(0 . "POINT") (cons 8 lay)
                 (cons 10 (list (car pt) (cadr pt) 0.0)))))

(defun dgm:circle (pt r lay)
  (entmake (list '(0 . "CIRCLE") (cons 8 lay)
                 (cons 10 (list (car pt) (cadr pt) 0.0))
                 (cons 40 r))))

;;; ------------------------ Βοηθητικές: γεωμετρία -----------------------

;; Κορυφές LWPOLYLINE ως λίστα (x y). Αφαιρεί διπλή τελευταία κορυφή.
(defun dgm:lwpts (e / d r g)
  (setq d (entget e) r nil)
  (foreach g d
    (if (= 10 (car g))
      (setq r (cons (list (cadr g) (caddr g)) r))))
  (setq r (reverse r))
  (if (and (> (length r) 1)
           (< (distance (car r) (last r)) 1e-8))
    (setq r (reverse (cdr (reverse r)))))
  r)

(defun dgm:closedp (e)
  (= 1 (logand 1 (cdr (assoc 70 (entget e))))))

;; Έχει τόξα (bulges);
(defun dgm:hasbulge (e / d g r)
  (setq d (entget e) r nil)
  (foreach g d
    (if (and (= 42 (car g)) (/= 0.0 (cdr g)))
      (setq r T)))
  r)

;; Εμβαδόν πολυγώνου (τύπος Gauss)
(defun dgm:area (pts / s n i p1 p2)
  (setq s 0.0 n (length pts) i 0)
  (while (< i n)
    (setq p1 (nth i pts)
          p2 (nth (rem (1+ i) n) pts))
    (setq s (+ s (- (* (car p1) (cadr p2)) (* (car p2) (cadr p1)))))
    (setq i (1+ i)))
  (abs (/ s 2.0)))

;; Απόσταση σημείου από ευθύγραμμο τμήμα a-b
(defun dgm:pseg (p a b / dx dy l2 tp q)
  (setq dx (- (car b) (car a))
        dy (- (cadr b) (cadr a)))
  (setq l2 (+ (* dx dx) (* dy dy)))
  (if (< l2 1e-12)
    (distance p a)
    (progn
      (setq tp (/ (+ (* (- (car p) (car a)) dx)
                     (* (- (cadr p) (cadr a)) dy))
                  l2))
      (if (< tp 0.0) (setq tp 0.0))
      (if (> tp 1.0) (setq tp 1.0))
      (setq q (list (+ (car a) (* tp dx)) (+ (cadr a) (* tp dy))))
      (distance p q))))

;; Σημείο μέσα σε πολύγωνο (ray casting)
(defun dgm:inpoly (p pts / n i j inside xi yi xj yj)
  (setq n (length pts) inside nil j (1- n) i 0)
  (while (< i n)
    (setq xi (car (nth i pts)) yi (cadr (nth i pts))
          xj (car (nth j pts)) yj (cadr (nth j pts)))
    (if (and (/= (> yi (cadr p)) (> yj (cadr p)))
             (< (car p)
                (+ xi (/ (* (- xj xi) (- (cadr p) yi)) (- yj yi)))))
      (setq inside (not inside)))
    (setq j i i (1+ i)))
  inside)

;;; ------------------------- Βοηθητικές: είσοδος ------------------------

;; Όταν dgm:*auto* = T (σύνθετες εντολές ροής, π.χ. DGMGEO) οι ερωτήσεις με
;; προεπιλογή απαντώνται σιωπηλά με την προεπιλεγμένη τιμή.
(defun dgm:getreal (msg def / v)
  (if dgm:*auto*
    def
    (progn
      (setq v (getreal (strcat msg " <" (rtos def 2 2) ">: ")))
      (if v v def))))

(defun dgm:getint (msg def / v)
  (if dgm:*auto*
    def
    (progn
      (setq v (getint (strcat msg " <" (itoa def) ">: ")))
      (if v v def))))

(defun dgm:getstr (msg def / v)
  (if dgm:*auto*
    def
    (progn
      (setq v (getstring T
                (strcat msg
                        (if (and def (/= def "")) (strcat " <" def ">") "")
                        ": ")))
      (if (= v "") def v))))

(defun dgm:sel-poly (msg / en)
  (setq en (entsel msg))
  (cond
    ((null en) nil)
    ((/= "LWPOLYLINE" (cdr (assoc 0 (entget (car en)))))
     (princ "\n** Το αντικείμενο δεν είναι LWPolyline. **")
     nil)
    (t (car en))))

;;; --------------------- Αναζήτηση αριθμών κορυφών ----------------------
;;; Διαβάζει τα κείμενα αρίθμησης από τα layers "σημείο_*" ώστε οι πίνακες
;;; να παίρνουν τους ίδιους αριθμούς με τα σημάδια του σχεδίου.

;; Είναι το string καθαρός ακέραιος (αριθμός κορυφής); Χρησιμεύει ώστε το
;; marks-load να αγνοεί άλλα κείμενα (π.χ. διαστάσεις πλευρών).
(defun dgm:intp (s / i c ok)
  (setq ok (> (strlen s) 0) i 1)
  (while (and ok (<= i (strlen s)))
    (setq c (ascii (substr s i 1)))
    (if (or (< c 48) (> c 57)) (setq ok nil))
    (setq i (1+ i)))
  ok)

;; Ανάλυση σειράς ακεραίων a..b σε αναλυτική απαρίθμηση "a, a+1, ..., b"
(defun dgm:expandrun (a b / r k)
  (setq r "" k a)
  (while (<= k b)
    (setq r (if (= r "") (itoa k) (strcat r ", " (itoa k))))
    (setq k (1+ k)))
  r)

;; Τμήμα περιγράμματος για μια σειρά: έως 5 συνεχόμενοι αριθμοί γράφονται
;; αναλυτικά, 6 ή περισσότεροι ενώνονται με "..."
(defun dgm:runseg (sstr snum last)
  (cond
    ((and snum last (> last snum))
     (if (<= (- last snum) 4)
       (dgm:expandrun snum last)
       (strcat sstr "..." (itoa last))))
    (t sstr)))

;; Περιγραφή περιγράμματος από τη σειρά των αριθμών κορυφών (nums) της
;; polyline: συνεχόμενες αριθμήσεις έως 5 γράφονται αναλυτικά, 6+ ενώνονται
;; με "...", και όταν διακόπτεται η σειρά μπαίνει κόμμα. Αν closed, κλείνει
;; με την πρώτη κορυφή.
(defun dgm:perimstr (nums closed / segs sstr snum last v s res)
  (setq segs nil sstr nil snum nil last nil)
  (foreach s nums
    (setq v (if (dgm:intp s) (atoi s)))
    (cond
      ((and v last (= v (1+ last))) (setq last v))
      (t
       (if sstr (setq segs (cons (dgm:runseg sstr snum last) segs)))
       (setq sstr s snum v last v))))
  (if sstr (setq segs (cons (dgm:runseg sstr snum last) segs)))
  (setq segs (reverse segs) res "")
  (foreach s segs (setq res (if (= res "") s (strcat res ", " s))))
  (if (and closed nums) (setq res (strcat res ", " (car nums))))
  res)

;; Ακτίνα κύκλου κορυφής και μετατόπιση αριθμού (μονάδες σχεδίου)
(if (null dgm:*vcirc*) (setq dgm:*vcirc* 0.4))
(if (null dgm:*voff*)  (setq dgm:*voff*  1.0))
;; Ανοχή αντιστοίχισης κορυφής<->σημαδιού. Τα σημάδια αποθηκεύονται στην
;; ΑΚΡΙΒΗ κορυφή (XDATA), οπότε μικρή ανοχή αρκεί - και δεν "πιάνει"
;; γειτονικές κορυφές (π.χ. στη μυτερή γωνία τριγώνου).
(if (null dgm:*findtol*) (setq dgm:*findtol* 0.02))

;; Λίστες αποφυγής επικάλυψης (αρχικοποιούνται σε κάθε εντολή αρίθμησης):
;; dgm:*placed* = τοποθετημένες ετικέτες (x y R), dgm:*segs* = τμήματα
;; polylines/lines προς αποφυγή.
(defun dgm:gathersegs (ss / segs i e pts np j lst)
  (setq segs nil i 0)
  (while (< i (sslength ss))
    (setq e (ssname ss i) pts (dgm:lwpts e) np (length pts) j 0)
    (while (< j (if (dgm:closedp e) np (1- np)))
      (setq segs (cons (list (nth j pts) (nth (rem (1+ j) np) pts)) segs))
      (setq j (1+ j)))
    (setq i (1+ i)))
  (setq lst (ssget "_X" '((0 . "LINE"))))
  (if lst
    (progn (setq i 0)
      (while (< i (sslength lst))
        (setq e (entget (ssname lst i)))
        (setq segs (cons (list (cdr (assoc 10 e)) (cdr (assoc 11 e))) segs))
        (setq i (1+ i)))))
  segs)

;; Αρχικοποίηση αποφυγής: τμήματα + ήδη υπάρχουσες ετικέτες σημείων
(defun dgm:avoid-init (ss / ssm i d ip)
  (setq dgm:*segs* (dgm:gathersegs ss))
  (setq dgm:*placed* nil)
  (setq ssm (ssget "_X" '((0 . "TEXT") (8 . "σημείο_*"))))
  (if ssm
    (progn (setq i 0)
      (while (< i (sslength ssm))
        (setq d (entget (ssname ssm i)) ip (cdr (assoc 10 d)))
        (if (dgm:intp (cdr (assoc 1 d)))
          (setq dgm:*placed* (cons (list (car ip) (cadr ip) 0.5) dgm:*placed*)))
        (setq i (1+ i))))))

;; Ελεύθερη θέση ετικέτας ακτίνας R στο κέντρο c (χωρίς επικάλυψη με
;; τοποθετημένες ετικέτες ή τμήματα)
(defun dgm:boxfree (c r / ok pl s)
  (setq ok T)
  (foreach pl dgm:*placed*
    (if (< (distance (list (car pl) (cadr pl)) c) (+ r (caddr pl)))
      (setq ok nil)))
  (if ok
    (foreach s dgm:*segs*
      (if (< (dgm:pseg c (car s) (cadr s)) r) (setq ok nil))))
  ok)

;; Κατεύθυνση "προς τα έξω" στην κορυφή idx (rad)
(defun dgm:outdir (v pts closed idx / np p nx ix iy l e)
  (setq np (length pts) ix 0.0 iy 0.0)
  (setq p  (if (or closed (> idx 0)) (nth (rem (+ idx (1- np)) np) pts))
        nx (if (or closed (< idx (1- np))) (nth (rem (1+ idx) np) pts)))
  (if p  (progn (setq l (distance p v))
                (if (> l 1e-9) (setq ix (+ ix (/ (- (car p) (car v)) l))
                                    iy (+ iy (/ (- (cadr p) (cadr v)) l))))))
  (if nx (progn (setq l (distance nx v))
                (if (> l 1e-9) (setq ix (+ ix (/ (- (car nx) (car v)) l))
                                    iy (+ iy (/ (- (cadr nx) (cadr v)) l))))))
  (setq l (sqrt (+ (* ix ix) (* iy iy))))
  (if (< l 1e-6)
    (progn                                   ; ευθύγραμμο/άκρο: κάθετο στην πλευρά
      (setq e (if nx nx p))
      (if e (setq ix (- (cadr e) (cadr v)) iy (- (car v) (car e)))
            (setq ix 1.0 iy 0.0))
      (atan iy ix))
    (atan (- iy) (- ix))))                   ; έξω = αντίθετο του "μέσα"

;; Τοποθέτηση αριθμού κορυφής μετατοπισμένου (dgm:*voff*) περιμετρικά, σε
;; θέση χωρίς επικάλυψη. Η ΑΚΡΙΒΗΣ κορυφή αποθηκεύεται ως XDATA (1010) ώστε
;; η αναζήτηση να παραμένει ακριβής ανεξάρτητα από τη μετατόπιση.
(defun dgm:placelabel (v pts closed idx h str lay / d r a0 angs da a pos found)
  (setq d dgm:*voff*
        r (+ (* 0.35 h (strlen str)) (* 0.6 h))
        a0 (dgm:outdir v pts closed idx))
  (if (and closed
           (dgm:inpoly (list (+ (car v) (* d (cos a0))) (+ (cadr v) (* d (sin a0)))) pts))
    (setq a0 (+ a0 pi)))
  (setq angs '(0.0 0.698 -0.698 1.396 -1.396 2.094 -2.094 3.14159) found nil)
  (foreach da angs
    (if (not found)
      (progn
        (setq a (+ a0 da)
              pos (list (+ (car v) (* d (cos a))) (+ (cadr v) (* d (sin a)))))
        (if (dgm:boxfree pos r) (setq found pos)))))
  (if (null found)
    (setq found (list (+ (car v) (* d (cos a0))) (+ (cadr v) (* d (sin a0))))))
  (regapp "GFDGM")
  (entmake (list '(0 . "TEXT") (cons 8 lay)
                 (cons 10 (list (car found) (cadr found) 0.0))
                 (cons 11 (list (car found) (cadr found) 0.0))
                 (cons 40 h) (cons 1 str) '(50 . 0.0) '(72 . 1) '(73 . 2)
                 (list -3 (list "GFDGM" (cons 1010 (list (car v) (cadr v) 0.0))))))
  (setq dgm:*placed* (cons (list (car found) (cadr found) r) dgm:*placed*))
  found)

;; Ανακτά τα σημάδια αρίθμησης ως ((x y) . αριθμός) στην ΑΚΡΙΒΗ κορυφή:
;; προτιμάται το XDATA (1010) του κειμένου· αν λείπει, η θέση του κειμένου.
;; Αγνοούνται μη-ακέραια κείμενα (π.χ. διαστάσεις).
(defun dgm:marks-load ( / ss i d s v)
  (setq dgm:*marks* nil)
  (setq ss (ssget "_X" '((0 . "TEXT") (8 . "σημείο_*"))))
  (if ss
    (progn
      (setq i 0)
      (while (< i (sslength ss))
        (setq d (entget (ssname ss i) '("GFDGM"))
              s (cdr (assoc 1 d)))
        (if (dgm:intp s)
          (progn
            (setq v (if (assoc -3 d)
                      (cdr (assoc 1010 (cdr (cadr (assoc -3 d)))))))
            (if (null v) (setq v (cdr (assoc 10 d))))
            (setq dgm:*marks* (cons (list (car v) (cadr v) s) dgm:*marks*))))
        (setq i (1+ i)))))
  dgm:*marks*)

;; Πλησιέστερο σημάδι στην κορυφή pt εντός ανοχής tol. Επειδή τα σημάδια
;; ανακτώνται στην ακριβή κορυφή, το πλησιέστερο είναι πάντα το σωστό ακόμη
;; και όταν δύο κορυφές απέχουν λιγότερο από την ανοχή.
(defun dgm:findnum (pt tol / best bd dd m)
  (setq best nil bd tol)
  (foreach m dgm:*marks*
    (setq dd (distance (list (car m) (cadr m)) pt))
    (if (< dd bd) (setq bd dd best (caddr m))))
  best)

;;; --------------------------- Μηχανή πινάκων ---------------------------
;;; ins   : πάνω-αριστερό σημείο
;;; title : τίτλος (string ή nil)
;;; heads : λίστα στηλών, κάθε στήλη = λίστα γραμμών κειμένου
;;; wids  : λίστα πλατών στηλών (μονάδες σχεδίου)
;;; rows  : λίστα γραμμών, κάθε γραμμή = λίστα strings
;;; h     : βασικό ύψος κειμένου, lay: layer

(defun dgm:fit-h (str w h / n)
  (setq n (max 1 (strlen str)))
  (min h (/ (* 0.95 w) (* 0.8 n))))

;; Τίτλος πίνακα: αν δεν χωρά σε μία γραμμή με το κανονικό ύψος, χωρίζεται
;; σε δύο γραμμές στο κενό που είναι πλησιέστερα στη μέση (αντί να μικραίνει).
(defun dgm:title2 (title tot h / n i best bd d)
  (if (<= (* 0.8 (strlen title) h) (* 0.95 tot))
    (list title)
    (progn
      (setq n (strlen title) i 1 best nil bd 1e9)
      (while (<= i n)
        (if (= (substr title i 1) " ")
          (progn
            (setq d (abs (- i (/ n 2))))
            (if (< d bd) (setq bd d best i))))
        (setq i (1+ i)))
      (if best
        (list (substr title 1 (1- best)) (substr title (1+ best)))
        (list title)))))

;; Ύψος της ζώνης τίτλου (μία ή δύο γραμμές)
(defun dgm:titleh (title tot h)
  (if (> (length (dgm:title2 title tot h)) 1) (* 4.2 h) (* 2.4 h)))

(defun dgm:table (ins title heads wids rows h lay footer
                  / tot x0 y0 th hh nhl y x i k w col row s ht yy tl tth)
  (setq tot (apply '+ wids)
        x0  (car ins)
        y0  (cadr ins)
        th  (* 2.0 h))
  (setq y y0)
  ;; Τίτλος
  (if (and title (/= title ""))
    (progn
      (setq tl (dgm:title2 title tot h)
            tth (dgm:titleh title tot h))
      (dgm:rect x0 (- y tth) (+ x0 tot) y lay)
      (if (> (length tl) 1)
        (progn
          (dgm:textc (list (+ x0 (/ tot 2.0)) (- y (* 1.2 h)))
                     (dgm:fit-h (car tl) tot h) (car tl) lay)
          (dgm:textc (list (+ x0 (/ tot 2.0)) (- y (* 3.0 h)))
                     (dgm:fit-h (cadr tl) tot h) (cadr tl) lay))
        (dgm:textc (list (+ x0 (/ tot 2.0)) (- y (* 1.2 h)))
                   (dgm:fit-h title tot h) title lay))
      (setq y (- y tth))))
  ;; Επικεφαλίδες
  (setq nhl (apply 'max (mapcar 'length heads)))
  (setq hh (* h (+ 1.2 (* 1.5 nhl))))
  (setq x x0 i 0)
  (foreach col heads
    (setq w (nth i wids))
    (setq k 0)
    (foreach s col
      (setq yy (- y (* h (+ 1.35 (* 1.5 k)))
                  (* 0.75 h (- nhl (length col))))) ; κατακόρυφο κεντράρισμα
      (dgm:textc (list (+ x (/ w 2.0)) yy)
                 (dgm:fit-h s w (* 0.9 h)) s lay)
      (setq k (1+ k)))
    (setq x (+ x w) i (1+ i)))
  ;; Γραμμές δεδομένων
  (setq yy (- y hh))
  (foreach row rows
    (setq x x0 i 0)
    (foreach s row
      (setq w (nth i wids))
      (if (/= s "")
        (dgm:textc (list (+ x (/ w 2.0)) (- yy (/ th 2.0)))
                   (dgm:fit-h s w (* 0.9 h)) s lay))
      (setq x (+ x w) i (1+ i)))
    (setq yy (- yy th)))
  ;; Πλέγμα
  ;; εξωτερικό πλαίσιο επικεφαλίδων + δεδομένων
  (dgm:rect x0 yy (+ x0 tot) y lay)
  ;; κατακόρυφες
  (setq x x0 i 0)
  (while (< i (1- (length wids)))
    (setq x (+ x (nth i wids)))
    (dgm:line (list x y) (list x yy) lay)
    (setq i (1+ i)))
  ;; οριζόντιες
  (dgm:line (list x0 (- y hh)) (list (+ x0 tot) (- y hh)) lay)
  (setq k 1)
  (while (< k (length rows))
    (dgm:line (list x0 (- y hh (* k th)))
              (list (+ x0 tot) (- y hh (* k th))) lay)
    (setq k (1+ k)))
  ;; προαιρετική τελική γραμμή εμβαδού (ενιαίο κελί σε όλο το πλάτος)
  (if footer
    (progn
      (dgm:rect x0 (- yy th) (+ x0 tot) yy lay)
      (dgm:textc (list (+ x0 (/ tot 2.0)) (- yy (/ th 2.0)))
                 (dgm:fit-h footer tot (* 0.9 h)) footer lay)))
  (princ))

;;; ============================ ΕΝΤΟΛΕΣ =================================

;;; DGML - Δημιουργία τυποποιημένων layers ανά τύπο διαγράμματος
(setq dgm:*lay-topo*
 '("BOUND_IMPL" "BOUND_UNIMPL" "PST_KAEK" "TOPO_PROP"
   "ROAD" "OT" "BLD" "VST" "EAS" "MINE" "OBJ"
   "DBOUND_RYM" "DBOUND_AIG" "DBOUND_PRL" "DBOUND_PAIG"
   "DBOUND_REM" "DBOUND_APAL" "DBOUND_PROP"
   "Ktiriaomora" "Mandra" "Syrma"
   "Bohthitikesgrammes" "pinakas_sintetagmenon"))

(setq dgm:*lay-dgm*
 (append dgm:*lay-topo*
  '("TOPO_PROP_NEW" "DGM_PROP_FINAL" "LINE_XM" "LINE_XM_VST"
    "AREA_A" "AREA_D" "AREA_A-labels" "AREA_D-labels"
    "AREA_A-hatch" "AREA_D-hatch"
    "VST_FINAL" "EAS_FINAL" "MINE_FINAL")))

(setq dgm:*lay-praksi*
 (append dgm:*lay-topo*
  '("TOPO_PROP_NEW" "DGM_PROP_FINAL" "LINE_XM" "LINE_XM_VST"
    "VST_FINAL" "EAS_FINAL" "MINE_FINAL")))

;; Layers που εμπλέκονται στην αρίθμηση κορυφών ενός ΔΓΜ. Οι κορυφές τους
;; αριθμούνται ΣΥΝΟΛΙΚΑ, ώστε ταυτιζόμενες κορυφές (αρχικό/τελικό/τμήματα)
;; να παίρνουν ΕΝΑΝ κοινό αριθμό.
(setq dgm:*lay-num*
 '("TOPO_PROP" "PST_KAEK" "DGM_PROP_FINAL" "AREA_A" "AREA_D"))

;; Ένωση λίστας ονομάτων σε συμβολοσειρά χωρισμένη με κόμματα (για φίλτρο ssget)
(defun dgm:joincommas (lst / s)
  (setq s "")
  (foreach x lst (setq s (if (= s "") x (strcat s "," x))))
  s)

(defun dgm:asktype ( / typ)
  (princ "\nΤύπος διαγράμματος:")
  (princ "\n  1 = Τοπογραφικό Διάγραμμα")
  (princ "\n  2 = ΔΓΜ (Διόρθωσης)")
  (princ "\n  3 = Διάγραμμα Πράξης")
  (dgm:getint "\nΕπιλογή" (if dgm:*typ* dgm:*typ* 2)))

(defun c:DGML ( / typ lst n)
  (setq typ (dgm:asktype))
  (setq dgm:*typ* typ)
  (setq lst (cond ((= typ 1) dgm:*lay-topo*)
                  ((= typ 3) dgm:*lay-praksi*)
                  (t dgm:*lay-dgm*)))
  (setq n 0)
  (foreach l lst
    (if (not (tblsearch "LAYER" l))
      (progn (dgm:layer-std l) (setq n (1+ n)))))
  (princ (strcat "\nΔημιουργήθηκαν " (itoa n) " νέα layers ("
                 (itoa (length lst)) " τυποποιημένα για τον τύπο αυτόν)."))
  (princ))

;; Ταύτιση κορυφών για την αρίθμηση: δύο κορυφές θεωρούνται ΙΔΙΑ κορυφή
;; (ένας αριθμός) όταν οι συντεταγμένες τους Χ και Υ διαφέρουν έως και tol
;; (π.χ. 0.001 m, συμπεριλαμβανομένου του ορίου - καλύπτει στρογγυλοποίηση
;; στο τρίτο δεκαδικό και στους δύο άξονες).
(defun dgm:samept (a b tol)
  (and (<= (abs (- (car a) (car b))) (+ tol 1e-6))
       (<= (abs (- (cadr a) (cadr b))) (+ tol 1e-6))))

;;; DGMK - Μαζική αρίθμηση κορυφών σε μία ή περισσότερες polylines.
;;; Κορυφές που ταυτίζονται (εντός ανοχής) παίρνουν ΕΝΑΝ αριθμό, και
;;; κορυφές με υπάρχον σημάδι από παλαιότερη αρίθμηση δεν ξανααριθμούνται.
;; Διαστάσεις πλευρών ως κείμενο παράλληλο στην πλευρά (ύψος h). Αποφυγή
;; διπλής αναγραφής κοινών πλευρών μέσω λίστας κλειδιών μέσων (done).
(defun dgm:sidedims (pts closed h lay done / n i a b dxx dyy len ar upx upy
                       mx my key)
  (setq n (length pts) i 0)
  (while (< i (if closed n (1- n)))
    (setq a (nth i pts) b (nth (rem (1+ i) n) pts))
    (setq dxx (- (car b) (car a)) dyy (- (cadr b) (cadr a))
          len (distance a b))
    (if (> len 1e-6)
      (progn
        ;; γωνία ανάγνωσης παράλληλη στην πλευρά, όρθια στο (-90,90]
        (setq ar (atan dyy dxx))
        (if (> ar (/ pi 2.0)) (setq ar (- ar pi)))
        (if (<= ar (- (/ pi 2.0))) (setq ar (+ ar pi)))
        (setq upx (- (sin ar)) upy (cos ar))
        (setq key (dgm:rkey (list (/ (+ (car a) (car b)) 2.0)
                                  (/ (+ (cadr a) (cadr b)) 2.0))))
        (if (not (member key done))
          (progn
            (setq mx (+ (/ (+ (car a) (car b)) 2.0) (* 0.6 h upx))
                  my (+ (/ (+ (cadr a) (cadr b)) 2.0) (* 0.6 h upy)))
            (dgm:textcr (list mx my) h (rtos len 2 2) lay ar)
            (setq done (cons key done))))))
    (setq i (1+ i)))
  done)

(defun c:DGMK ( / ss tol h n i e lay mlay a pts pt done f dd
                  cnt skipdup skipex dims dseen closed np k)
  (princ (strcat "\nΕπιλέξτε polylines για αρίθμηση κορυφών "
                 "(ENTER = όλα τα layers ΔΓΜ: "
                 (dgm:joincommas dgm:*lay-num*) "): "))
  (setq ss (ssget '((0 . "LWPOLYLINE"))))
  ;; Χωρίς επιλογή -> όλες οι polylines των layers που εμπλέκονται στο ΔΓΜ,
  ;; ώστε η αρίθμηση να γίνει ΣΥΝΟΛΙΚΑ (κοινές κορυφές = ένας αριθμός).
  (if (null ss)
    (progn
      (setq ss (ssget "_X" (list '(0 . "LWPOLYLINE")
                                 (cons 8 (dgm:joincommas dgm:*lay-num*)))))
      (if ss
        (princ (strcat "\nΕπιλέχθηκαν αυτόματα "
                       (itoa (sslength ss))
                       " polylines των layers ΔΓΜ.")))))
  (if ss
    (progn
      (setq h (dgm:getreal "\nΎψος κειμένου αρίθμησης" dgm:*h*))
      (setq dgm:*h* h)
      (setq tol (dgm:getreal "\nΑνοχή ταύτισης κορυφών (m)" 0.001))
      (setq dims (dgm:getint "\nΤοποθέτηση διαστάσεων πλευρών; 1 = Ναι, 0 = Όχι" 0))
      (setq n (dgm:getint "\nΑριθμός πρώτης κορυφής" (1+ dgm:*num*)))
      (dgm:marks-load)
      (dgm:avoid-init ss)
      (setq done nil cnt 0 skipdup 0 skipex 0)
      (setq i 0)
      (while (< i (sslength ss))
        (setq e (ssname ss i))
        (setq lay  (cdr (assoc 8 (entget e)))
              mlay (strcat "σημείο_" lay)
              a    (assoc mlay dgm:*layers*))
        (dgm:layer mlay (if a (cadr a) 3))
        (setq pts (dgm:lwpts e) closed (dgm:closedp e) np (length pts) k 0)
        (while (< k np)
          (setq pt (nth k pts))
          (setq f nil)
          (foreach dd done
            (if (dgm:samept dd pt tol) (setq f T)))
          (cond
            ;; κοινή κορυφή - αριθμήθηκε ήδη σε αυτή την εκτέλεση
            (f (setq skipdup (1+ skipdup)))
            ;; έχει ήδη σημάδι αρίθμησης από παλαιότερη εκτέλεση
            ((dgm:findnum pt dgm:*findtol*)
             (setq done (cons pt done))
             (setq skipex (1+ skipex)))
            ;; νέα κορυφή
            (t
             (dgm:point pt mlay)
             (dgm:circle pt dgm:*vcirc* mlay)
             (dgm:placelabel pt pts closed k h (itoa n) mlay)
             (setq done (cons pt done))
             (setq n (1+ n) cnt (1+ cnt))))
          (setq k (1+ k)))
        (setq i (1+ i)))
      (if (> cnt 0) (setq dgm:*num* (1- n)))
      (princ (strcat "\nΑριθμήθηκαν " (itoa cnt) " νέες κορυφές σε "
                     (itoa (sslength ss)) " polylines. Τελευταίος αριθμός: "
                     (itoa dgm:*num*)))
      (if (> skipdup 0)
        (princ (strcat "\nΚοινές κορυφές που πήραν έναν αριθμό: "
                       (itoa skipdup))))
      (if (> skipex 0)
        (princ (strcat "\nΚορυφές με υπάρχουσα αρίθμηση που διατηρήθηκαν: "
                       (itoa skipex))))
      ;; διαστάσεις πλευρών (μόνο κείμενο, παράλληλο στην πλευρά)
      (if (= dims 1)
        (progn
          (setq dseen nil i 0)
          (while (< i (sslength ss))
            (setq e (ssname ss i))
            (setq lay (strcat "diast_" (cdr (assoc 8 (entget e)))))
            (dgm:layer lay 3)
            (setq dseen (dgm:sidedims (dgm:lwpts e) (dgm:closedp e) h lay dseen))
            (setq i (1+ i)))
          (princ "\nΤοποθετήθηκαν διαστάσεις πλευρών παράλληλα στις πλευρές.")))))
  (princ))

;;; DGMP - Πίνακας συντεταγμένων κορυφών
(defun c:DGMP ( / en pts h typ kaek tmima title nums ok n i p q rows row
                  maxr len ng rowsper mrows heads wids ins g idx d)
  (setq en (dgm:sel-poly "\nΕπιλέξτε polyline για πίνακα συντεταγμένων: "))
  (if en
    (progn
      (setq pts (dgm:lwpts en))
      (setq h (dgm:getreal "\nΎψος κειμένου πίνακα" dgm:*h*))
      (setq dgm:*h* h)
      (princ "\nΤύπος πίνακα:")
      (princ "\n  1 = Αρχικό γεωτεμάχιο με ΚΑΕΚ")
      (princ "\n  2 = Τελικό γεωτεμάχιο (ενημέρωση κτηματολογικής βάσης)")
      (princ "\n  3 = Αποκοπτόμενο τμήμα")
      (princ "\n  4 = Διεκδικούμενο τμήμα")
      (princ "\n  5 = Πίνακας κορυφών ιδιοκτησίας")
      (princ "\n  6 = Ελεύθερος τίτλος")
      (setq typ (dgm:getint "\nΕπιλογή" 1))
      (cond
        ((= typ 1)
         (setq kaek (dgm:getstr "\nΚΑΕΚ" ""))
         (setq title (strcat "ΠΙΝΑΚΑΣ ΣΥΝΤΕΤΑΓΜΕΝΩΝ ΚΟΡΥΦΩΝ ΑΡΧΙΚΟΥ ΓΕΩΤΕΜΑΧΙΟΥ ΜΕ ΚΑΕΚ " kaek)))
        ((= typ 2)
         (setq kaek (dgm:getstr "\nΚΑΕΚ" ""))
         (setq title (strcat "ΠΙΝΑΚΑΣ ΣΥΝΤΕΤΑΓΜΕΝΩΝ ΚΟΡΥΦΩΝ ΤΕΛΙΚΟΥ ΓΕΩΤΕΜΑΧΙΟΥ ΜΕ ΚΑΕΚ " kaek
                              " ΓΙΑ ΤΗΝ ΕΝΗΜΕΡΩΣΗ ΤΗΣ ΚΤΗΜΑΤΟΛΟΓΙΚΗΣ ΒΑΣΗΣ")))
        ((= typ 3)
         (setq tmima (dgm:getstr "\nΌνομα τμήματος (π.χ. Α1)" "Α1"))
         (setq kaek (dgm:getstr "\nΑπό ΚΑΕΚ" ""))
         (setq title (strcat "ΠΙΝΑΚΑΣ ΣΥΝΤΕΤΑΓΜΕΝΩΝ ΚΟΡΥΦΩΝ ΑΠΟΚΟΠΤΟΜΕΝΟΥ ΤΜΗΜΑΤΟΣ "
                             tmima " ΑΠΟ ΚΑΕΚ " kaek)))
        ((= typ 4)
         (setq tmima (dgm:getstr "\nΌνομα τμήματος (π.χ. Δ1)" "Δ1"))
         (setq kaek (dgm:getstr "\nΑπό ΚΑΕΚ" ""))
         (setq title (strcat "ΠΙΝΑΚΑΣ ΣΥΝΤΕΤΑΓΜΕΝΩΝ ΚΟΡΥΦΩΝ ΔΙΕΚΔΙΚΟΥΜΕΝΟΥ ΤΜΗΜΑΤΟΣ "
                             tmima " ΑΠΟ ΚΑΕΚ " kaek)))
        ((= typ 5)
         (setq title "ΠΙΝΑΚΑΣ ΚΟΡΥΦΩΝ ΙΔΙΟΚΤΗΣΙΑΣ"))
        (t
         (setq title (dgm:getstr "\nΤίτλος πίνακα" "ΠΙΝΑΚΑΣ ΣΥΝΤΕΤΑΓΜΕΝΩΝ ΚΟΡΥΦΩΝ"))))
      ;; Αριθμοί κορυφών: πρώτα από τα σημάδια "σημείο_*", αλλιώς διαδοχική αρίθμηση
      (dgm:marks-load)
      (setq nums nil ok T)
      (foreach p pts
        (setq n (dgm:findnum p dgm:*findtol*))
        (if (null n) (setq ok nil))
        (setq nums (cons n nums)))
      (setq nums (reverse nums))
      (if (not ok)
        (progn
          (princ "\nΔεν βρέθηκαν σημάδια αρίθμησης για όλες τις κορυφές.")
          (setq n (dgm:getint "\nΑριθμός πρώτης κορυφής" 1))
          (setq nums nil i 0)
          (while (< i (length pts))
            (setq nums (cons (itoa (+ n i)) nums))
            (setq i (1+ i)))
          (setq nums (reverse nums))))
      ;; Γραμμές πίνακα
      (setq rows nil i 0)
      (while (< i (length pts))
        (setq p (nth i pts))
        (setq d (if (> i 0)
                  (strcat (nth (1- i) nums) " - " (nth i nums) ": "
                          (rtos (distance (nth (1- i) pts) p) 2 2))
                  ""))
        (setq rows (cons (list (nth i nums)
                               (rtos (car p) 2 3)
                               (rtos (cadr p) 2 3)
                               d)
                         rows))
        (setq i (1+ i)))
      (setq rows (reverse rows))
      (if (dgm:closedp en)
        (setq rows
              (append rows
                      (list (list "" "" ""
                                  (strcat (last nums) " - " (car nums) ": "
                                          (rtos (distance (last pts) (car pts)) 2 2)))))))
      ;; Σπάσιμο σε πολλαπλές ομάδες στηλών αν οι γραμμές είναι πολλές
      (setq maxr (dgm:getint "\nΜέγιστες γραμμές ανά ομάδα στηλών" 30))
      (setq len (length rows))
      (setq ng (1+ (/ (1- len) maxr)))
      (setq rowsper (1+ (/ (1- len) ng)))
      (setq mrows nil i 0)
      (while (< i rowsper)
        (setq row nil g 0)
        (while (< g ng)
          (setq idx (+ i (* g rowsper)))
          (setq row (append row
                            (if (< idx len)
                              (nth idx rows)
                              (list "" "" "" ""))))
          (setq g (1+ g)))
        (setq mrows (cons row mrows))
        (setq i (1+ i)))
      (setq mrows (reverse mrows))
      (setq heads nil wids nil g 0)
      (while (< g ng)
        (setq heads (append heads
                            (list (list "Σημείο") (list "Χ") (list "Y")
                                  (list "Αποστάσεις"))))
        (setq wids (append wids
                           (list (* 8 h) (* 16 h) (* 16 h) (* 17 h))))
        (setq g (1+ g)))
      (setq ins (getpoint "\nΣημείο εισαγωγής πίνακα (πάνω αριστερή γωνία): "))
      (if ins
        (progn
          (dgm:layer-std "pinakas_sintetagmenon")
          (dgm:table ins title heads wids mrows h "pinakas_sintetagmenon"
                     (if (dgm:closedp en)
                       (strcat "Ε (" (dgm:perimstr nums T) ") = "
                               (rtos (dgm:area pts) 2 2) " τ.μ.")
                       nil))
          (princ (strcat "\nΟ πίνακας δημιουργήθηκε ("
                         (itoa (length pts)) " κορυφές)."))))))
  (princ))

;;; DGME - Πίνακας αρχικών και τελικών εμβαδών
(defun c:DGME ( / h rows kaek e1 e2 v1 v2 ins heads wids en)
  (setq h (dgm:getreal "\nΎψος κειμένου πίνακα" dgm:*h*))
  (setq dgm:*h* h)
  (setq rows nil)
  (setq kaek (getstring T "\nΚΑΕΚ γεωτεμαχίου (Enter για τέλος): "))
  (while (/= kaek "")
    ;; αρχικό εμβαδόν
    (setq en (entsel "\nΑρχική γεωμετρία - επιλέξτε polyline (Enter για πληκτρολόγηση): "))
    (if (and en (= "LWPOLYLINE" (cdr (assoc 0 (entget (car en))))))
      (setq v1 (rtos (dgm:area (dgm:lwpts (car en))) 2 2))
      (setq v1 (dgm:getstr "\nΑρχικό εμβαδόν (τ.μ.)" "")))
    ;; τελικό εμβαδόν
    (setq en (entsel "\nΤελική γεωμετρία - επιλέξτε polyline (Enter για πληκτρολόγηση): "))
    (if (and en (= "LWPOLYLINE" (cdr (assoc 0 (entget (car en))))))
      (setq v2 (rtos (dgm:area (dgm:lwpts (car en))) 2 2))
      (setq v2 (dgm:getstr "\nΤελικό εμβαδόν (τ.μ.)" "-")))
    (setq rows (cons (list kaek v1 v2) rows))
    (setq kaek (getstring T "\nΚΑΕΚ γεωτεμαχίου (Enter για τέλος): ")))
  (setq rows (reverse rows))
  (if rows
    (progn
      (setq heads (list (list "ΕΜΠΛΕΚΟΜΕΝΑ ΚΑΕΚ")
                        (list "ΑΡΧΙΚΟ ΕΜΒΑΔΟΝ" "(τ.μ.)")
                        (list "ΤΕΛΙΚΟ ΕΜΒΑΔΟΝ ΜΕΤΑ ΤΗ" "ΔΙΟΡΘΩΣΗ ΤΩΝ ΟΡΙΩΝ ΒΑΣΕΙ"
                              "ΑΙΤΗΣΗΣ / ΔΙΚΟΓΡΑΦΟΥ (τ.μ.)")))
      (setq wids (list (* 22 h) (* 16 h) (* 26 h)))
      (setq ins (getpoint "\nΣημείο εισαγωγής πίνακα (πάνω αριστερή γωνία): "))
      (if ins
        (progn
          (dgm:layer-std "pinakas_sintetagmenon")
          (dgm:table ins "ΠΙΝΑΚΑΣ ΑΡΧΙΚΩΝ ΚΑΙ ΤΕΛΙΚΩΝ ΕΜΒΑΔΩΝ ΕΠΗΡΕΑΖΟΜΕΝΩΝ ΓΕΩΤΕΜΑΧΙΩΝ"
                     heads wids rows h "pinakas_sintetagmenon" nil)
          (princ (strcat "\nΟ πίνακας δημιουργήθηκε (" (itoa (length rows))
                         " γεωτεμάχια)."))))))
  (princ))

;;; DGMT - Πίνακας για τη διόρθωση των γεωτεμαχίων
(defun c:DGMT ( / h rows nm en v from to ins heads wids)
  (setq h (dgm:getreal "\nΎψος κειμένου πίνακα" dgm:*h*))
  (setq dgm:*h* h)
  (setq rows nil)
  (setq nm (getstring T "\nΌνομα τμήματος π.χ. Α1 (Enter για τέλος): "))
  (while (/= nm "")
    (setq en (entsel "\nΕπιλέξτε polyline τμήματος (Enter για πληκτρολόγηση εμβαδού): "))
    (if (and en (= "LWPOLYLINE" (cdr (assoc 0 (entget (car en))))))
      (setq v (rtos (dgm:area (dgm:lwpts (car en))) 2 2))
      (setq v (dgm:getstr "\nΕμβαδόν τμήματος (τ.μ.)" "")))
    (setq from (dgm:getstr "\nΑΠΟ ΚΑΕΚ" ""))
    (setq to   (dgm:getstr "\nΣΕ ΚΑΕΚ" ""))
    (setq rows (cons (list nm v from to) rows))
    (setq nm (getstring T "\nΌνομα τμήματος (Enter για τέλος): ")))
  (setq rows (reverse rows))
  (if rows
    (progn
      (setq heads (list (list "ΤΜΗΜΑ")
                        (list "ΕΜΒΑΔΟΝ" "(τ.μ.)")
                        (list "ΑΠΟ ΚΑΕΚ")
                        (list "ΣΕ ΚΑΕΚ")))
      (setq wids (list (* 10 h) (* 14 h) (* 18 h) (* 18 h)))
      (setq ins (getpoint "\nΣημείο εισαγωγής πίνακα (πάνω αριστερή γωνία): "))
      (if ins
        (progn
          (dgm:layer-std "pinakas_sintetagmenon")
          (dgm:table ins "ΠΙΝΑΚΑΣ ΓΙΑ ΤΗ ΔΙΟΡΘΩΣΗ ΤΩΝ ΓΕΩΤΕΜΑΧΙΩΝ"
                     heads wids rows h "pinakas_sintetagmenon" nil)
          (princ "\nΟ πίνακας δημιουργήθηκε.")))))
  (princ))

;;; DGMA - Χαρακτηρισμός τμήματος (αποκοπτόμενο/διεκδικούμενο)
(defun c:DGMA ( / en typ lay lablay nm h pt d)
  (setq en (dgm:sel-poly "\nΕπιλέξτε polyline τμήματος: "))
  (if en
    (progn
      (princ "\nΤύπος τμήματος:  1 = Αποκοπτόμενο (Α)   2 = Διεκδικούμενο (Δ)")
      (setq typ (dgm:getint "\nΕπιλογή" 1))
      (if (= typ 2)
        (setq lay "AREA_D" lablay "AREA_D-labels")
        (setq lay "AREA_A" lablay "AREA_A-labels"))
      (dgm:layer-std lay)
      (dgm:layer-std lablay)
      (setq nm (dgm:getstr "\nΌνομα τμήματος" (if (= typ 2) "Δ1" "Α1")))
      ;; μεταφορά polyline στο σωστό layer
      (setq d (entget en))
      (entmod (subst (cons 8 lay) (assoc 8 d) d))
      ;; ετικέτα
      (setq h (dgm:getreal "\nΎψος κειμένου ετικέτας" dgm:*h*))
      (setq dgm:*h* h)
      (setq pt (getpoint "\nΘέση ετικέτας: "))
      (if pt (dgm:textc pt h (strcat "ΤΜΗΜΑ " nm) lablay))
      (princ (strcat "\nΤο τμήμα " nm " μεταφέρθηκε στο layer " lay
                     " (Εμβαδόν: "
                     (rtos (dgm:area (dgm:lwpts en)) 2 2) " τ.μ.)"))))
  (princ))

;;; DGMKAEK - Τοποθέτηση κειμένου ΚΑΕΚ
(defun c:DGMKAEK ( / s typ lay h pt)
  (setq s (getstring T "\nΚΑΕΚ: "))
  (if (/= 12 (strlen s))
    (princ (strcat "\n** Προσοχή: ο ΚΑΕΚ έχει " (itoa (strlen s))
                   " χαρακτήρες αντί για 12. **")))
  (princ "\nLayer:  1 = PST_KAEK (επηρεαζόμενο)   2 = PST (όμορο)")
  (setq typ (dgm:getint "\nΕπιλογή" 1))
  (setq lay (if (= typ 2) "PST" "PST_KAEK"))
  (dgm:layer-std lay)
  (setq h (dgm:getreal "\nΎψος κειμένου" dgm:*h*))
  (setq dgm:*h* h)
  (setq pt (getpoint "\nΘέση κειμένου ΚΑΕΚ: "))
  (if pt
    (progn
      (dgm:text pt h s lay)
      (princ (strcat "\nΤοποθετήθηκε ΚΑΕΚ " s " στο layer " lay))))
  (princ))

;;; Κανόνες οντοτήτων ανά layer: (όνομα δέχεται-polyline μόνο-κλειστές δέχεται-κείμενο)
(setq dgm:*layrules*
 '(("PST_KAEK"       T   T   T)
   ("DGM_PROP_FINAL" T   T   nil)
   ("TOPO_PROP"      T   T   nil)
   ("TOPO_PROP_NEW"  T   T   nil)
   ("AREA_A"         T   T   nil)
   ("AREA_D"         T   T   nil)
   ("BLD"            T   T   T)
   ("VST"            T   T   T)
   ("EAS"            T   T   T)
   ("MINE"           T   T   nil)
   ("VST_FINAL"      T   T   nil)
   ("EAS_FINAL"      T   T   nil)
   ("MINE_FINAL"     T   T   nil)
   ("LINE_XM"        T   nil nil)
   ("LINE_XM_VST"    T   nil nil)
   ("BOUND_IMPL"     T   nil nil)
   ("BOUND_UNIMPL"   T   nil nil)
   ("DBOUND_PROP"    T   T   T)
   ("ROAD"           nil nil T)
   ("OT"             nil nil T)
   ("AREA_A-labels"  nil nil T)
   ("AREA_D-labels"  nil nil T)))

;; Είναι ο χαρακτήρας ψηφίο;
(defun dgm:digitp (c) (and (>= (ascii c) 48) (<= (ascii c) 57)))

(defun dgm:alldigits (s from to / i ok)
  (setq ok T i from)
  (while (<= i to)
    (if (not (dgm:digitp (substr s i 1))) (setq ok nil))
    (setq i (1+ i)))
  ok)

;; Μορφή κειμένου στο PST_KAEK: 'KAEK 'NEO 'TRYPA ή nil (λάθος μορφή)
(defun dgm:kaekfmt (s)
  (cond
    ((and (>= (strlen s) 3) (= (substr s 1 3) "ΝΕΟ")) 'NEO)
    ((and (>= (strlen s) 5) (= (substr s 1 5) "ΤΡΥΠΑ")) 'TRYPA)
    ((/= 12 (strlen s)) nil)
    ((dgm:alldigits s 1 12) 'KAEK)
    ((and (dgm:alldigits s 1 5)
          (= (substr s 6 2) "ΕΚ")
          (dgm:alldigits s 8 12))
     'KAEK)
    (t nil)))

;;; DGMC - Έλεγχος ορθότητας σχεδίου πριν την υποβολή
(defun c:DGMC ( / tol typ req rule ktexts tx kc nc tc island ip p2 pair labs
                  ss i e d et lay nerr nwarn polys texts pts p
                  pstpolys pstsegs finpolys segs a b j k dd mind found
                  sum1 sum2 cnt inpts)
  ;; καθάρισμα παλιών σημαδιών ελέγχου
  (setq ss (ssget "_X" '((8 . "DGM_CHECK"))))
  (if ss
    (progn
      (setq i 0)
      (while (< i (sslength ss))
        (entdel (ssname ss i))
        (setq i (1+ i)))))
  (dgm:layer "DGM_CHECK" 1)
  (setq typ (dgm:asktype))
  (setq dgm:*typ* typ)
  (setq tol (dgm:getreal "\nΑνοχή ταύτισης κορυφών (m)" 0.001))
  (setq nerr 0 nwarn 0)
  (princ "\n================= ΕΛΕΓΧΟΣ ΟΡΘΟΤΗΤΑΣ =================")
  ;; 1. Υποχρεωτικά layers με οντότητες, ανά τύπο διαγράμματος
  (setq req (cond
              ((= typ 1) '("BOUND_IMPL" "BOUND_UNIMPL" "PST_KAEK" "TOPO_PROP"))
              ((= typ 3) '("BOUND_IMPL" "BOUND_UNIMPL" "PST_KAEK"
                           "TOPO_PROP" "TOPO_PROP_NEW"))
              (t '("BOUND_IMPL" "BOUND_UNIMPL" "PST_KAEK"
                   "TOPO_PROP" "TOPO_PROP_NEW" "DGM_PROP_FINAL"))))
  (foreach lay req
    (if (null (ssget "_X" (list (cons 8 lay))))
      (progn
        (princ (strcat "\n[ΣΦΑΛΜΑ] Δεν υπάρχει οντότητα στο layer " lay))
        (setq nerr (1+ nerr)))))
  (if (= typ 2)
    (if (and (null (ssget "_X" '((8 . "AREA_A"))))
             (null (ssget "_X" '((8 . "AREA_D")))))
      (progn
        (princ "\n[ΣΦΑΛΜΑ] Απαιτείται τουλάχιστον ένα από τα layers AREA_A / AREA_D με οντότητες.")
        (setq nerr (1+ nerr)))))
  (if (= typ 3)
    (if (not (or (ssget "_X" '((8 . "LINE_XM")))
                 (ssget "_X" '((8 . "LINE_XM_VST")))
                 (ssget "_X" '((8 . "VST_FINAL")))
                 (ssget "_X" '((8 . "EAS_FINAL")))
                 (ssget "_X" '((8 . "MINE_FINAL")))
                 (ssget "_X" '((8 . "DGM_PROP_FINAL")))))
      (progn
        (princ "\n[ΣΦΑΛΜΑ] Απαιτείται τουλάχιστον ένα από τα layers LINE_XM / LINE_XM_VST / VST_FINAL / EAS_FINAL / MINE_FINAL / DGM_PROP_FINAL.")
        (setq nerr (1+ nerr)))))
  ;; 2. Έλεγχος οντοτήτων ανά layer βάσει επιτρεπόμενων τύπων
  (foreach rule dgm:*layrules*
    (setq lay (car rule))
    (setq ss (ssget "_X" (list (cons 8 lay))))
    (if ss
      (progn
        (setq i 0 polys 0 texts 0)
        (while (< i (sslength ss))
          (setq e (ssname ss i)
                d (entget e)
                et (cdr (assoc 0 d)))
          (cond
            ((= et "LWPOLYLINE")
             (setq polys (1+ polys))
             (setq pts (dgm:lwpts e))
             (if (not (cadr rule))
               (progn
                 (princ (strcat "\n[ΣΦΑΛΜΑ] Το layer " lay
                                " δέχεται μόνο κείμενα - βρέθηκε polyline."))
                 (dgm:mkpoly pts "DGM_CHECK" (dgm:closedp e))
                 (setq nerr (1+ nerr))))
             (if (and (caddr rule) (not (dgm:closedp e)))
               (progn
                 (princ (strcat "\n[ΣΦΑΛΜΑ] Ανοιχτή polyline στο layer " lay
                                " κοντά στο σημείο ("
                                (rtos (caar pts) 2 2) ", "
                                (rtos (cadar pts) 2 2) ")"))
                 (dgm:circle (car pts) 2.0 "DGM_CHECK")
                 (setq nerr (1+ nerr))))
             (if (dgm:hasbulge e)
               (progn
                 (princ (strcat "\n[ΠΡΟΣΟΧΗ] Polyline με τόξα (bulges) στο layer " lay))
                 (setq nwarn (1+ nwarn))))
             ;; μηδενικά τμήματα / διπλές κορυφές
             (setq j 0)
             (while (< j (1- (length pts)))
               (if (< (distance (nth j pts) (nth (1+ j) pts)) 1e-6)
                 (progn
                   (princ (strcat "\n[ΠΡΟΣΟΧΗ] Διπλή κορυφή στο layer " lay
                                  " στο σημείο ("
                                  (rtos (car (nth j pts)) 2 2) ", "
                                  (rtos (cadr (nth j pts)) 2 2) ")"))
                   (dgm:circle (nth j pts) 2.0 "DGM_CHECK")
                   (setq nwarn (1+ nwarn))))
               (setq j (1+ j))))
            ((or (= et "TEXT") (= et "MTEXT"))
             (setq texts (1+ texts))
             (cond
               ((member lay '("DGM_PROP_FINAL" "TOPO_PROP"))
                (princ (strcat "\n[ΣΦΑΛΜΑ] Δεν επιτρέπεται κείμενο στο layer "
                               lay " (ΔΓΜ)."))
                (dgm:circle (cdr (assoc 10 d)) 2.0 "DGM_CHECK")
                (setq nerr (1+ nerr)))
               ((not (cadddr rule))
                (princ (strcat "\n[ΠΡΟΣΟΧΗ] Κείμενο στο layer " lay
                               " - το layer δεν προβλέπει κείμενα."))
                (setq nwarn (1+ nwarn)))))
            ((or (= et "LINE") (= et "ARC") (= et "SPLINE")
                 (= et "POLYLINE") (= et "ELLIPSE") (= et "CIRCLE"))
             (princ (strcat "\n[ΣΦΑΛΜΑ] Οντότητα " et " στο layer " lay
                            " - τα όρια πρέπει να είναι LWPolylines."))
             (setq nerr (1+ nerr))))
          (setq i (1+ i)))
        (princ (strcat "\n[INFO] Layer " lay ": " (itoa polys)
                       " polylines, " (itoa texts) " κείμενα.")))))
  ;; 3. Κείμενα ΚΑΕΚ: μορφή και αντιστοίχιση με πολύγωνα
  (setq pstpolys nil ktexts nil)
  (setq ss (ssget "_X" '((8 . "PST_KAEK"))))
  (if ss
    (progn
      (setq i 0)
      (while (< i (sslength ss))
        (setq e (ssname ss i)
              d (entget e)
              et (cdr (assoc 0 d)))
        (cond
          ((= et "LWPOLYLINE")
           (if (dgm:closedp e)
             (setq pstpolys (cons (dgm:lwpts e) pstpolys))))
          ((or (= et "TEXT") (= et "MTEXT"))
           (setq ktexts (cons (cons (list (cadr (assoc 10 d))
                                          (caddr (assoc 10 d)))
                                    (cdr (assoc 1 d)))
                              ktexts))))
        (setq i (1+ i)))))
  ;; 3α. Μορφή κειμένων ΚΑΕΚ
  (foreach tx ktexts
    (if (null (dgm:kaekfmt (cdr tx)))
      (progn
        (princ (strcat "\n[ΣΦΑΛΜΑ] Κείμενο με λάθος μορφή στο PST_KAEK: \""
                       (cdr tx)
                       "\" (12 ψηφία, 5ψηφ+ΕΚ+5ψηφ, ΝΕΟ... ή ΤΡΥΠΑ...)"))
        (dgm:circle (car tx) 2.0 "DGM_CHECK")
        (setq nerr (1+ nerr)))))
  ;; 3β. Κάθε υφιστάμενος ΚΑΕΚ πρέπει να βρίσκεται εντός πολυγώνου PST_KAEK
  (foreach tx ktexts
    (if (eq 'KAEK (dgm:kaekfmt (cdr tx)))
      (progn
        (setq found nil)
        (foreach pts pstpolys
          (if (dgm:inpoly (car tx) pts) (setq found T)))
        (if (not found)
          (progn
            (princ (strcat "\n[ΣΦΑΛΜΑ] Ο ΚΑΕΚ " (cdr tx)
                           " δεν βρίσκεται εντός πολυγώνου PST_KAEK."))
            (dgm:circle (car tx) 2.0 "DGM_CHECK")
            (setq nerr (1+ nerr)))))))
  ;; 3γ. Πολύγωνα PST_KAEK: ακριβώς ένας υφιστάμενος ΚΑΕΚ (νησίδες/ΤΡΥΠΑ εξαιρούνται)
  (foreach pts pstpolys
    (setq kc 0 tc 0 island nil)
    (foreach tx ktexts
      (if (dgm:inpoly (car tx) pts)
        (cond
          ((eq 'KAEK (dgm:kaekfmt (cdr tx))) (setq kc (1+ kc)))
          ((eq 'TRYPA (dgm:kaekfmt (cdr tx))) (setq tc (1+ tc))))))
    (if (= kc 0)
      (progn
        (setq ip (dgm:innerpt pts))
        (foreach p2 pstpolys
          (if (and ip (not (eq p2 pts)) (dgm:inpoly ip p2))
            (setq island T)))
        (cond
          ((> tc 0)
           (princ "\n[INFO] Πολύγωνο PST_KAEK χαρακτηρισμένο ως ΤΡΥΠΑ."))
          (island
           (princ "\n[ΠΡΟΣΟΧΗ] Νησίδα PST_KAEK χωρίς ΚΑΕΚ - θα εμφανιστεί ως ΑΓΝΩΣΤΟ ΚΑΕΚ.")
           (setq nwarn (1+ nwarn)))
          (t
           (princ "\n[ΣΦΑΛΜΑ] Πολύγωνο PST_KAEK χωρίς κείμενο ΚΑΕΚ στο εσωτερικό του.")
           (dgm:circle (car pts) 2.0 "DGM_CHECK")
           (setq nerr (1+ nerr)))))
      (if (> kc 1)
        (progn
          (princ "\n[ΣΦΑΛΜΑ] Πολύγωνο PST_KAEK με περισσότερα από ένα κείμενα ΚΑΕΚ.")
          (dgm:circle (car pts) 2.0 "DGM_CHECK")
          (setq nerr (1+ nerr))))))
  ;; 3δ. Πολύγωνα DGM_PROP_FINAL: ένας (ΝΕΟ ή υφιστάμενος) ΚΑΕΚ, όχι και τα δύο
  (setq ss (ssget "_X" '((0 . "LWPOLYLINE") (8 . "DGM_PROP_FINAL"))))
  (if ss
    (progn
      (setq i 0)
      (while (< i (sslength ss))
        (setq e (ssname ss i))
        (if (dgm:closedp e)
          (progn
            (setq pts (dgm:lwpts e) kc 0 nc 0)
            (foreach tx ktexts
              (if (dgm:inpoly (car tx) pts)
                (cond
                  ((eq 'KAEK (dgm:kaekfmt (cdr tx))) (setq kc (1+ kc)))
                  ((eq 'NEO (dgm:kaekfmt (cdr tx))) (setq nc (1+ nc))))))
            (cond
              ((and (= kc 0) (= nc 0))
               (princ "\n[ΣΦΑΛΜΑ] Πολύγωνο DGM_PROP_FINAL χωρίς ΚΑΕΚ (ΝΕΟ ή υφιστάμενο) στο εσωτερικό του.")
               (dgm:circle (car pts) 2.0 "DGM_CHECK")
               (setq nerr (1+ nerr)))
              ((> nc 1)
               (princ "\n[ΣΦΑΛΜΑ] Πολύγωνο DGM_PROP_FINAL με περισσότερα από ένα κείμενα ΝΕΟ.")
               (dgm:circle (car pts) 2.0 "DGM_CHECK")
               (setq nerr (1+ nerr)))
              ((and (>= kc 1) (>= nc 1))
               (princ "\n[ΣΦΑΛΜΑ] Πολύγωνο DGM_PROP_FINAL με ΝΕΟ και υφιστάμενο ΚΑΕΚ ταυτόχρονα.")
               (dgm:circle (car pts) 2.0 "DGM_CHECK")
               (setq nerr (1+ nerr))))))
        (setq i (1+ i)))))
  ;; 3ε. Πολύγωνα AREA_A/AREA_D πρέπει να περιέχουν ετικέτα στο αντίστοιχο layer labels
  (foreach pair '(("AREA_A" . "AREA_A-labels") ("AREA_D" . "AREA_D-labels"))
    (setq labs nil)
    (setq ss (ssget "_X" (list '(0 . "TEXT,MTEXT") (cons 8 (cdr pair)))))
    (if ss
      (progn
        (setq i 0)
        (while (< i (sslength ss))
          (setq d (entget (ssname ss i)))
          (setq labs (cons (list (cadr (assoc 10 d)) (caddr (assoc 10 d))) labs))
          (setq i (1+ i)))))
    (setq ss (ssget "_X" (list '(0 . "LWPOLYLINE") (cons 8 (car pair)))))
    (if ss
      (progn
        (setq i 0)
        (while (< i (sslength ss))
          (setq e (ssname ss i))
          (if (dgm:closedp e)
            (progn
              (setq pts (dgm:lwpts e) cnt 0)
              (foreach p labs
                (if (dgm:inpoly p pts) (setq cnt (1+ cnt))))
              (if (= cnt 0)
                (progn
                  (princ (strcat "\n[ΣΦΑΛΜΑ] Πολύγωνο " (car pair)
                                 " χωρίς ετικέτα στο layer " (cdr pair) "."))
                  (dgm:circle (car pts) 2.0 "DGM_CHECK")
                  (setq nerr (1+ nerr))))))
          (setq i (1+ i))))))
  ;; 4. Κορυφές DGM_PROP_FINAL πάνω στα όρια PST_KAEK
  (setq pstsegs nil)
  (foreach pts pstpolys
    (setq j 0 k (length pts))
    (while (< j k)
      (setq pstsegs (cons (list (nth j pts) (nth (rem (1+ j) k) pts)) pstsegs))
      (setq j (1+ j))))
  (setq finpolys nil)
  (setq ss (ssget "_X" '((0 . "LWPOLYLINE") (8 . "DGM_PROP_FINAL"))))
  (if ss
    (progn
      (setq i 0)
      (while (< i (sslength ss))
        (setq finpolys (cons (dgm:lwpts (ssname ss i)) finpolys))
        (setq i (1+ i)))))
  (if (and pstsegs finpolys)
    (progn
      (setq cnt 0 inpts 0)
      (foreach pts finpolys
        (foreach p pts
          (setq mind 1e99)
          (foreach segs pstsegs
            (setq dd (dgm:pseg p (car segs) (cadr segs)))
            (if (< dd mind) (setq mind dd)))
          (cond
            ((<= mind tol) (setq cnt (1+ cnt)))
            ((<= mind 0.10)
             (princ (strcat "\n[ΠΡΟΣΟΧΗ] Κορυφή DGM_PROP_FINAL σε απόσταση "
                            (rtos mind 2 3) " m από όριο PST_KAEK ("
                            (rtos (car p) 2 2) ", " (rtos (cadr p) 2 2)
                            ") - πιθανή αστοχία ταύτισης."))
             (dgm:circle p 2.0 "DGM_CHECK")
             (setq nwarn (1+ nwarn)))
            (t (setq inpts (1+ inpts))))))
      (princ (strcat "\n[INFO] DGM_PROP_FINAL: " (itoa cnt)
                     " κορυφές πάνω στα όρια PST_KAEK, " (itoa inpts)
                     " κορυφές εκτός ορίων (νέα/εσωτερικά όρια)."))))
  ;; 5. Σύγκριση εμβαδών
  (setq sum1 0.0)
  (foreach pts pstpolys (setq sum1 (+ sum1 (dgm:area pts))))
  (setq sum2 0.0)
  (foreach pts finpolys (setq sum2 (+ sum2 (dgm:area pts))))
  (if (and pstpolys finpolys)
    (progn
      (princ (strcat "\n[INFO] Άθροισμα εμβαδών PST_KAEK: "
                     (rtos sum1 2 2) " τ.μ."))
      (princ (strcat "\n[INFO] Άθροισμα εμβαδών DGM_PROP_FINAL: "
                     (rtos sum2 2 2) " τ.μ."))
      (princ (strcat "\n[INFO] Διαφορά: " (rtos (- sum2 sum1) 2 2) " τ.μ."))))
  ;; Σύνοψη
  (princ (strcat "\n======================================================"
                 "\nΣΦΑΛΜΑΤΑ: " (itoa nerr)
                 "   ΠΡΟΕΙΔΟΠΟΙΗΣΕΙΣ: " (itoa nwarn)))
  (if (or (> nerr 0) (> nwarn 0))
    (princ "\nΤα προβληματικά σημεία επισημάνθηκαν με κύκλους στο layer DGM_CHECK."))
  (textscr)
  (princ))

;;; ==================== ΧΩΡΙΚΕΣ ΠΡΑΞΕΙΣ ΠΟΛΥΓΩΝΩΝ ======================
;;; Οι πράξεις βασίζονται σε "ακύρωση" των κοινών πλευρών (XOR): οι πλευρές
;;; που εμφανίζονται και στα δύο πολύγωνα αφαιρούνται και οι υπόλοιπες
;;; αλυσιδώνονται σε νέο κλειστό περίγραμμα. Προϋπόθεση (όπως και στις
;;; προδιαγραφές): τα κοινά όρια να έχουν ταυτισμένες κορυφές εντός ανοχής.

;; Δημιουργία LWPOLYLINE
(defun dgm:mkpoly (pts lay closed)
  (entmake (append (list '(0 . "LWPOLYLINE")
                         '(100 . "AcDbEntity")
                         (cons 8 lay)
                         '(100 . "AcDbPolyline")
                         (cons 90 (length pts))
                         (cons 70 (if closed 1 0)))
                   (mapcar '(lambda (p) (cons 10 (list (car p) (cadr p))))
                           pts))))

;; Κλειδί σημείου (στρογγυλοποίηση 4 δεκαδικών = 0.1 mm)
(defun dgm:rkey (p)
  (strcat (rtos (car p) 2 4) "_" (rtos (cadr p) 2 4)))

;; Αφαίρεση συγκεκριμένου στοιχείου (κατά eq) από λίστα
(defun dgm:rm (item lst / out x)
  (setq out nil)
  (foreach x lst (if (not (eq x item)) (setq out (cons x out))))
  (reverse out))

;; Ταξινόμηση λίστας ζευγών (key . data) κατά αύξον αριθμητικό key
(defun dgm:sortpairs (lst / sorted item out x done)
  (setq sorted nil)
  (foreach item lst
    (setq out nil done nil)
    (foreach x sorted
      (if (and (not done) (< (car item) (car x)))
        (setq out (cons item out) done T))
      (setq out (cons x out)))
    (if (not done) (setq out (cons item out)))
    (setq sorted (reverse out)))
  sorted)

;; Απαλοιφή διαδοχικών διπλών κορυφών (και τελευταίας = πρώτης)
(defun dgm:dedup (pts / out p)
  (setq out nil)
  (foreach p pts
    (if (or (null out) (> (distance p (car out)) 1e-8))
      (setq out (cons p out))))
  (setq out (reverse out))
  (if (and (> (length out) 1)
           (< (distance (car out) (last out)) 1e-8))
    (setq out (reverse (cdr (reverse out)))))
  out)

;; "Κανονικοποίηση" σημείου: όλα τα σημεία εντός tol ταυτίζονται
(defun dgm:canon (p tol / found c)
  (setq found nil)
  (foreach c dgm:*canon*
    (if (and (not found) (< (distance c p) tol)) (setq found c)))
  (if found
    found
    (progn (setq dgm:*canon* (cons p dgm:*canon*)) p)))

;; Πύκνωση πολυγώνου: σπάει κάθε πλευρά στα σημεία της allpts που
;; βρίσκονται πάνω της (εντός tol)
(defun dgm:densify (pts allpts tol / n i a b mids p out)
  (setq n (length pts) i 0 out nil)
  (while (< i n)
    (setq a (nth i pts) b (nth (rem (1+ i) n) pts))
    (setq out (cons a out))
    (setq mids nil)
    (foreach p allpts
      (if (and (> (distance p a) tol)
               (> (distance p b) tol)
               (< (dgm:pseg p a b) tol))
        (setq mids (cons (cons (distance a p) p) mids))))
    (foreach p (dgm:sortpairs mids)
      (setq out (cons (cdr p) out)))
    (setq i (1+ i)))
  (reverse out))

;; Επόμενη κορυφή κατά τη δεξιόστροφη διάσχιση όψεων επίπεδου γραφήματος:
;; από την κατευθυνόμενη πλευρά kprev->kcur επιλέγεται η αμέσως επόμενη
;; δεξιόστροφα πλευρά γύρω από την kcur.
(defun dgm:nextcw (kprev kcur adj verts / pp pc thin best bestd th d c)
  (setq pp (cdr (assoc kprev verts))
        pc (cdr (assoc kcur verts)))
  (setq thin (atan (- (cadr pp) (cadr pc)) (- (car pp) (car pc))))
  (setq best nil bestd 1e99)
  (foreach c (cdr (assoc kcur adj))
    (setq th (car c) d (- thin th))
    (while (<= d 1e-9) (setq d (+ d 6.283185307179586)))
    (while (> d 6.283185307179586) (setq d (- d 6.283185307179586)))
    (if (< d bestd) (setq bestd d best (cdr c))))
  best)

;; XOR πλευρών πολυγώνων: επιστρέφει λίστα κλειστών βρόχων (όψεις CCW).
;; Οι κοινές πλευρές ακυρώνονται, οι πλευρές τέμνονται στα σημεία τομής τους
;; και οι εναπομείνασες αλυσιδώνονται με γωνιακή διάσχιση όψεων.
(defun dgm:xorloops (polys tol / cpolys pts p allpts dpolys edges n i a b k
                       rec loops verts adj ka kb cell th used dirs d0
                       face kprev kcur knext guard pts2
                       ia ib ptsa ptsb na nb j c d ip)
  (setq dgm:*canon* nil)
  ;; κανονικοποίηση κορυφών
  (setq cpolys nil)
  (foreach pts polys
    (setq cpolys (cons (mapcar '(lambda (p) (dgm:canon p tol)) pts) cpolys)))
  ;; τομές πλευρών μεταξύ διαφορετικών πολυγώνων -> νέα κοινά σημεία
  (setq ia 0)
  (foreach ptsa cpolys
    (setq ib 0)
    (foreach ptsb cpolys
      (if (> ib ia)
        (progn
          (setq na (length ptsa) nb (length ptsb) i 0)
          (while (< i na)
            (setq a (nth i ptsa) b (nth (rem (1+ i) na) ptsa))
            (setq j 0)
            (while (< j nb)
              (setq c (nth j ptsb) d (nth (rem (1+ j) nb) ptsb))
              (setq ip (inters a b c d T))
              (if ip (dgm:canon (list (car ip) (cadr ip)) tol))
              (setq j (1+ j)))
            (setq i (1+ i)))))
      (setq ib (1+ ib)))
    (setq ia (1+ ia)))
  (setq allpts dgm:*canon*)
  ;; πύκνωση με τις κορυφές όλων των πολυγώνων
  (setq dpolys nil)
  (foreach pts cpolys
    (setq dpolys (cons (dgm:densify pts allpts tol) dpolys)))
  ;; συλλογή πλευρών με XOR (η 2η εμφάνιση ακυρώνει την 1η)
  (setq edges nil)
  (foreach pts dpolys
    (setq n (length pts) i 0)
    (while (< i n)
      (setq a (nth i pts) b (nth (rem (1+ i) n) pts))
      (if (> (distance a b) (* 0.5 tol))
        (progn
          (setq k (if (< (dgm:rkey a) (dgm:rkey b))
                    (strcat (dgm:rkey a) "|" (dgm:rkey b))
                    (strcat (dgm:rkey b) "|" (dgm:rkey a))))
          (if (setq rec (assoc k edges))
            (setq edges (dgm:rm rec edges))
            (setq edges (cons (list k a b) edges)))))
      (setq i (1+ i))))
  ;; κατασκευή λιστών γειτνίασης (κορυφή -> γωνίες προς γείτονες)
  (setq verts nil adj nil)
  (foreach rec edges
    (setq a (cadr rec) b (caddr rec)
          ka (dgm:rkey a) kb (dgm:rkey b))
    (if (not (assoc ka verts)) (setq verts (cons (cons ka a) verts)))
    (if (not (assoc kb verts)) (setq verts (cons (cons kb b) verts)))
    (setq th (atan (- (cadr b) (cadr a)) (- (car b) (car a))))
    (setq cell (assoc ka adj))
    (if cell
      (setq adj (subst (cons ka (cons (cons th kb) (cdr cell))) cell adj))
      (setq adj (cons (list ka (cons th kb)) adj)))
    (setq th (atan (- (cadr a) (cadr b)) (- (car a) (car b))))
    (setq cell (assoc kb adj))
    (if cell
      (setq adj (subst (cons kb (cons (cons th ka) (cdr cell))) cell adj))
      (setq adj (cons (list kb (cons th ka)) adj))))
  ;; εξαγωγή όψεων με γωνιακή διάσχιση - κρατάμε τις CCW (εσωτερικές)
  (setq used nil loops nil dirs nil)
  (foreach rec edges
    (setq ka (dgm:rkey (cadr rec)) kb (dgm:rkey (caddr rec)))
    (setq dirs (cons (cons ka kb) (cons (cons kb ka) dirs))))
  (foreach d0 dirs
    (if (not (member (strcat (car d0) ">" (cdr d0)) used))
      (progn
        (setq face (list (car d0) (cdr d0)))
        (setq used (cons (strcat (car d0) ">" (cdr d0)) used))
        (setq kprev (car d0) kcur (cdr d0) guard 0)
        (while (and face (< guard 100000))
          (setq guard (1+ guard))
          (setq knext (dgm:nextcw kprev kcur adj verts))
          (cond
            ((null knext) (setq face nil))
            ((and (= kcur (car d0)) (= knext (cdr d0)))
             (setq guard 100000))
            (t
             (setq used (cons (strcat kcur ">" knext) used))
             (setq face (append face (list knext)))
             (setq kprev kcur kcur knext))))
        (if face
          (progn
            (setq pts2 (dgm:dedup
                         (mapcar '(lambda (k) (cdr (assoc k verts))) face)))
            (if (and (> (length pts2) 2) (> (dgm:sarea pts2) 1e-9))
              (setq loops (cons pts2 loops))))))))
  loops)

;; Επιλογή πολλών κλειστών polylines
(defun dgm:selpolys (msg / ss i out e)
  (princ msg)
  (setq ss (ssget '((0 . "LWPOLYLINE"))))
  (setq out nil)
  (if ss
    (progn
      (setq i 0)
      (while (< i (sslength ss))
        (setq e (ssname ss i))
        (if (dgm:closedp e)
          (setq out (cons (dgm:lwpts e) out))
          (princ "\n[ΠΡΟΣΟΧΗ] Παραλείφθηκε ανοιχτή polyline."))
        (setq i (1+ i)))))
  out)

;;; DGMUNION - Συνένωση όμορων πολυγώνων
(defun c:DGMUNION ( / polys tol loops lay pts)
  (setq polys (dgm:selpolys "\nΕπιλέξτε 2 ή περισσότερα όμορα κλειστά πολύγωνα: "))
  (if (< (length polys) 2)
    (princ "\n** Χρειάζονται τουλάχιστον 2 κλειστά πολύγωνα. **")
    (progn
      (setq tol (dgm:getreal "\nΑνοχή ταύτισης κορυφών (m)" 0.001))
      (setq loops (dgm:xorloops polys tol))
      (cond
        ((null loops)
         (princ "\n** Δεν προέκυψε αποτέλεσμα. **"))
        ((= (length loops) (length polys))
         (princ "\n** Τα πολύγωνα δεν έχουν κοινές πλευρές (με την ανοχή αυτή) - δεν έγινε συνένωση. **"))
        (t
         (setq lay (dgm:getstr "\nLayer αποτελέσματος" "DGM_PROP_FINAL"))
         (dgm:layer-std lay)
         (foreach pts loops
           (dgm:mkpoly pts lay T)
           (princ (strcat "\nΝέο πολύγωνο: " (itoa (length pts))
                          " κορυφές, εμβαδόν "
                          (rtos (dgm:area pts) 2 2) " τ.μ.")))
         (princ (strcat "\nΔημιουργήθηκαν " (itoa (length loops))
                        " πολύγωνα στο layer " lay "."))))))
  (princ))

;;; DGMCUT - Αποκοπή τμήματος από γεωτεμάχιο
(defun c:DGMCUT ( / e1 e2 p1 p2 tol loops lay pts expct)
  (setq e1 (dgm:sel-poly "\nΕπιλέξτε το γεωτεμάχιο: "))
  (if e1
    (progn
      (setq e2 (dgm:sel-poly "\nΕπιλέξτε το αποκοπτόμενο τμήμα: "))
      (if e2
        (if (or (not (dgm:closedp e1)) (not (dgm:closedp e2)))
          (princ "\n** Και τα δύο πολύγωνα πρέπει να είναι κλειστά. **")
          (progn
            (setq p1 (dgm:lwpts e1) p2 (dgm:lwpts e2))
            (setq tol (dgm:getreal "\nΑνοχή ταύτισης κορυφών (m)" 0.001))
            (setq expct (- (dgm:area p1) (dgm:area p2)))
            (setq loops (dgm:xorloops (list p1 p2) tol))
            (cond
              ((or (null loops) (/= 1 (length loops)))
               (princ "\n** Η αποκοπή δεν έδωσε ενιαίο πολύγωνο. **")
               (princ "\nΕλέγξτε ότι το τμήμα εφάπτεται στο όριο του γεωτεμαχίου")
               (princ "\nμε ταυτισμένες κορυφές (όχι εσωτερική νησίδα)."))
              (t
               (setq lay (dgm:getstr "\nLayer αποτελέσματος" "DGM_PROP_FINAL"))
               (dgm:layer-std lay)
               (setq pts (car loops))
               (dgm:mkpoly pts lay T)
               (princ (strcat "\nΥπόλοιπο γεωτεμάχιο στο layer " lay ": "
                              (rtos (dgm:area pts) 2 2)
                              " τ.μ. (αναμενόμενο: "
                              (rtos expct 2 2) " τ.μ.)")))))))))
  (princ))

;;; DGMSPLIT - Κατάτμηση πολυγώνου με γραμμή κοπής
(defun c:DGMSPLIT ( / en ec pts cpts n m ints i j k a b c d ip f rec two
                      sorted i1 i2 t1 t2 pt1 pt2 mid fwd bwd pa pb lay del)
  (setq en (dgm:sel-poly "\nΕπιλέξτε το κλειστό πολύγωνο προς κατάτμηση: "))
  (if (and en (not (dgm:closedp en)))
    (progn (princ "\n** Η polyline δεν είναι κλειστή. **") (setq en nil)))
  (setq ec (if en
             (dgm:sel-poly "\nΕπιλέξτε τη γραμμή κοπής (polyline που διαπερνά το πολύγωνο): ")))
  (if (and en ec)
    (progn
      (setq pts (dgm:lwpts en) cpts (dgm:lwpts ec))
      (setq n (length pts) m (length cpts))
      ;; εύρεση τομών γραμμής κοπής με το περίγραμμα
      (setq ints nil i 0)
      (while (< i n)
        (setq a (nth i pts) b (nth (rem (1+ i) n) pts))
        (setq j 0)
        (while (< j (1- m))
          (setq c (nth j cpts) d (nth (1+ j) cpts))
          (setq ip (inters a b c d T))
          (if ip
            (progn
              (setq ip (list (car ip) (cadr ip)))
              (setq f nil)
              (foreach rec ints
                (if (< (distance (nth 4 rec) ip) 1e-6) (setq f T)))
              (if (not f)
                (setq ints (cons (list i
                                       (distance a ip)
                                       j
                                       (+ (* 1000000.0 j) (distance c ip))
                                       ip)
                                 ints)))))
          (setq j (1+ j)))
        (setq i (1+ i)))
      (if (/= 2 (length ints))
        (princ (strcat "\n** Βρέθηκαν " (itoa (length ints))
                       " σημεία τομής - υποστηρίζεται κοπή με ακριβώς 2. "
                       "Η γραμμή πρέπει να διαπερνά πλήρως το πολύγωνο. **"))
        (progn
          ;; ταξινόμηση των 2 τομών κατά μήκος της γραμμής κοπής
          (setq sorted (dgm:sortpairs
                         (mapcar '(lambda (x) (cons (cadddr x) x)) ints)))
          (setq rec (cdr (car sorted)) two (cdr (cadr sorted)))
          (setq i1 (car rec) t1 (cadr rec) pt1 (nth 4 rec)
                i2 (car two) t2 (cadr two) pt2 (nth 4 two))
          ;; ενδιάμεσες κορυφές της γραμμής κοπής μεταξύ των 2 τομών
          (setq mid nil j (1+ (caddr rec)))
          (while (<= j (caddr two))
            (setq mid (append mid (list (nth j cpts))))
            (setq j (1+ j)))
          ;; εμπρόσθια διαδρομή περιγράμματος pt1 -> pt2
          (cond
            ((and (= i1 i2) (< t1 t2)) (setq fwd nil))
            ((= i1 i2)
             (setq fwd nil j (rem (1+ i1) n) k 0)
             (while (< k n)
               (setq fwd (append fwd (list (nth j pts)))
                     j (rem (1+ j) n) k (1+ k))))
            (t
             (setq fwd nil j (rem (1+ i1) n))
             (while (/= j (rem (1+ i2) n))
               (setq fwd (append fwd (list (nth j pts)))
                     j (rem (1+ j) n)))))
          ;; οπίσθια διαδρομή περιγράμματος pt2 -> pt1
          (cond
            ((and (= i1 i2) (> t1 t2)) (setq bwd nil))
            ((= i1 i2)
             (setq bwd nil j (rem (1+ i2) n) k 0)
             (while (< k n)
               (setq bwd (append bwd (list (nth j pts)))
                     j (rem (1+ j) n) k (1+ k))))
            (t
             (setq bwd nil j (rem (1+ i2) n))
             (while (/= j (rem (1+ i1) n))
               (setq bwd (append bwd (list (nth j pts)))
                     j (rem (1+ j) n)))))
          ;; σύνθεση των δύο νέων πολυγώνων
          (setq pa (dgm:dedup (append (list pt1) fwd (list pt2) (reverse mid))))
          (setq pb (dgm:dedup (append (list pt2) bwd (list pt1) mid)))
          (setq lay (dgm:getstr "\nLayer αποτελεσμάτων"
                                (cdr (assoc 8 (entget en)))))
          (dgm:layer-std lay)
          (dgm:mkpoly pa lay T)
          (dgm:mkpoly pb lay T)
          (princ (strcat "\nΤμήμα 1: " (rtos (dgm:area pa) 2 2)
                         " τ.μ.   Τμήμα 2: " (rtos (dgm:area pb) 2 2)
                         " τ.μ.   (Αρχικό: "
                         (rtos (dgm:area pts) 2 2) " τ.μ.)"))
          (princ "\nΔιαγραφή αρχικού πολυγώνου;  1 = Όχι   2 = Ναι")
          (setq del (dgm:getint "\nΕπιλογή" 1))
          (if (= del 2) (entdel en))))))
  (princ))

;;; ===================== HASH DXF / ΚΗΔ =================================

;; Αφαίρεση κενών από string
(defun dgm:nospace (s / out i c)
  (setq out "" i 1)
  (while (<= i (strlen s))
    (setq c (substr s i 1))
    (if (/= c " ") (setq out (strcat out c)))
    (setq i (1+ i)))
  out)

;;; DGMHASH - Υπολογισμός hash SHA512 αρχείου DXF μέσω certutil
(defun c:DGMHASH ( / dxf algname tmp cmd ok sh f line hash pt h)
  (setq dxf (getfiled "Επιλογή αρχείου DXF" "" "dxf" 0))
  (if dxf
    (progn
      (setq algname "SHA512")
      (setq tmp (strcat (getenv "TEMP") "\\dgm_hash.txt"))
      (setq cmd (strcat "cmd /c certutil -hashfile \"" dxf "\" " algname
                        " > \"" tmp "\""))
      (setq ok nil)
      (if vl-load-com (vl-load-com))
      (if vlax-create-object
        (progn
          (setq sh (vlax-create-object "WScript.Shell"))
          (if sh
            (progn
              (vlax-invoke-method sh 'Run cmd 0 :vlax-true)
              (vlax-release-object sh)
              (setq ok T)))))
      (if (not ok)
        (progn
          (startapp cmd)
          (getstring "\nΟ υπολογισμός τρέχει σε παράθυρο cmd. Πατήστε Enter όταν ολοκληρωθεί... ")))
      ;; ανάγνωση αποτελέσματος
      (setq hash nil)
      (setq f (open tmp "r"))
      (if f
        (progn
          (read-line f)                      ; γραμμή τίτλου certutil
          (setq line (read-line f))          ; γραμμή με το hash
          (close f)
          (if line (setq hash (dgm:nospace line)))))
      (if (and hash (= 128 (strlen hash)))
        (progn
          (princ (strcat "\n" algname ": " hash))
          (setq pt (getpoint "\nΘέση κειμένου hash στο σχέδιο (Enter για παράλειψη): "))
          (if pt
            (progn
              (setq h (dgm:getreal "\nΎψος κειμένου" dgm:*h*))
              (setq dgm:*h* h)
              (dgm:text pt h (strcat algname " DXF: " hash)
                        (getvar "CLAYER")))))
        (princ "\n** Δεν ήταν δυνατή η ανάγνωση του hash. Δοκιμάστε το tools/dxf-hash.cmd εκτός CAD. **"))))
  (princ))

;;; DGMKHD - Τοποθέτηση ΚΗΔ (Κωδικός Ηλεκτρονικού Διαγράμματος) στο σχέδιο
(defun c:DGMKHD ( / s pt h)
  (setq s (getstring T "\nΚΗΔ (Κωδικός Ηλεκτρονικού Διαγράμματος): "))
  (if (/= s "")
    (progn
      (setq h (dgm:getreal "\nΎψος κειμένου" dgm:*h*))
      (setq dgm:*h* h)
      (setq pt (getpoint "\nΘέση κειμένου: "))
      (if pt (dgm:text pt h (strcat "ΚΗΔ: " s) (getvar "CLAYER")))))
  (princ))

;;; ============== ΕΡΓΑΛΕΙΑ ΡΟΗΣ ΕΡΓΑΣΙΑΣ (τύπου KtimaDGM) ===============

;; Προσημασμένο εμβαδόν (θετικό = CCW)
(defun dgm:sarea (pts / s n i p1 p2)
  (setq s 0.0 n (length pts) i 0)
  (while (< i n)
    (setq p1 (nth i pts) p2 (nth (rem (1+ i) n) pts))
    (setq s (+ s (- (* (car p1) (cadr p2)) (* (car p2) (cadr p1)))))
    (setq i (1+ i)))
  (/ s 2.0))

;; Περίμετρος κλειστού πολυγώνου
(defun dgm:perim (pts / s n i)
  (setq s 0.0 n (length pts) i 0)
  (while (< i n)
    (setq s (+ s (distance (nth i pts) (nth (rem (1+ i) n) pts))))
    (setq i (1+ i)))
  s)

;; Αντιπροσωπευτικό εσωτερικό σημείο κλειστού βρόχου
(defun dgm:innerpt (pts / n i a b len mx my nx ny p)
  (setq n (length pts) i 0 p nil)
  (while (and (< i n) (null p))
    (setq a (nth i pts) b (nth (rem (1+ i) n) pts))
    (setq len (distance a b))
    (if (> len 1e-9)
      (progn
        (setq mx (/ (+ (car a) (car b)) 2.0)
              my (/ (+ (cadr a) (cadr b)) 2.0)
              nx (/ (- (cadr a) (cadr b)) len)
              ny (/ (- (car b) (car a)) len))
        (foreach ee (list (* 0.01 len) (* 0.001 len) 0.005)
          (if (null p)
            (cond
              ((dgm:inpoly (list (+ mx (* ee nx)) (+ my (* ee ny))) pts)
               (setq p (list (+ mx (* ee nx)) (+ my (* ee ny)))))
              ((dgm:inpoly (list (- mx (* ee nx)) (- my (* ee ny))) pts)
               (setq p (list (- mx (* ee nx)) (- my (* ee ny))))))))))
    (setq i (1+ i)))
  p)

;; Θέση σημείου πάνω στο περίγραμμα: (iedge . απόσταση από αρχή πλευράς) ή nil
(defun dgm:onboundary (p pts tol / n i a b res)
  (setq n (length pts) i 0 res nil)
  (while (and (< i n) (null res))
    (setq a (nth i pts) b (nth (rem (1+ i) n) pts))
    (if (< (dgm:pseg p a b) tol)
      (setq res (cons i (distance a p))))
    (setq i (1+ i)))
  res)

;; Ελάχιστη απόσταση σημείου από περίγραμμα πολυγώνου
(defun dgm:pmindist (p pts / n i a b d md)
  (setq n (length pts) i 0 md 1e99)
  (while (< i n)
    (setq a (nth i pts) b (nth (rem (1+ i) n) pts))
    (setq d (dgm:pseg p a b))
    (if (< d md) (setq md d))
    (setq i (1+ i)))
  md)

;; Μήκος κοινού ορίου βρόχου loop με πολύγωνο pts
(defun dgm:sharedlen (loop pts tol / n i a b m tot)
  (setq n (length loop) i 0 tot 0.0)
  (while (< i n)
    (setq a (nth i loop) b (nth (rem (1+ i) n) loop))
    (setq m (list (/ (+ (car a) (car b)) 2.0)
                  (/ (+ (cadr a) (cadr b)) 2.0)))
    (if (< (dgm:pmindist m pts) tol)
      (setq tot (+ tot (distance a b))))
    (setq i (1+ i)))
  tot)

;; Κοπή κλειστού πολυγώνου pts με χορδή cpts (άκρα πάνω στο περίγραμμα)
;; Επιστρέφει (pa pb) ή nil
(defun dgm:splitchord (pts cpts tol / n pt1 pt2 e1 e2 i1 t1 i2 t2 mid
                         fwd bwd j k pa pb)
  (setq n (length pts)
        pt1 (car cpts)
        pt2 (last cpts))
  (setq e1 (dgm:onboundary pt1 pts tol)
        e2 (dgm:onboundary pt2 pts tol))
  (if (and e1 e2 (> (length cpts) 1))
    (progn
      (setq i1 (car e1) t1 (cdr e1)
            i2 (car e2) t2 (cdr e2))
      (setq mid (reverse (cdr (reverse (cdr cpts)))))
      (cond
        ((and (= i1 i2) (< t1 t2)) (setq fwd nil))
        ((= i1 i2)
         (setq fwd nil j (rem (1+ i1) n) k 0)
         (while (< k n)
           (setq fwd (append fwd (list (nth j pts)))
                 j (rem (1+ j) n) k (1+ k))))
        (t
         (setq fwd nil j (rem (1+ i1) n))
         (while (/= j (rem (1+ i2) n))
           (setq fwd (append fwd (list (nth j pts)))
                 j (rem (1+ j) n)))))
      (cond
        ((and (= i1 i2) (> t1 t2)) (setq bwd nil))
        ((= i1 i2)
         (setq bwd nil j (rem (1+ i2) n) k 0)
         (while (< k n)
           (setq bwd (append bwd (list (nth j pts)))
                 j (rem (1+ j) n) k (1+ k))))
        (t
         (setq bwd nil j (rem (1+ i2) n))
         (while (/= j (rem (1+ i1) n))
           (setq bwd (append bwd (list (nth j pts)))
                 j (rem (1+ j) n)))))
      (setq pa (dgm:dedup (append (list pt1) fwd (list pt2) (reverse mid))))
      (setq pb (dgm:dedup (append (list pt2) bwd (list pt1) mid)))
      (if (and (> (length pa) 2) (> (length pb) 2))
        (list pa pb)))))

;; Συγχρονισμένη εκτέλεση εντολής Windows
(defun dgm:runsync (cmd / ok sh)
  (setq ok nil)
  (if vl-load-com (vl-load-com))
  (if vlax-create-object
    (progn
      (setq sh (vlax-create-object "WScript.Shell"))
      (if sh
        (progn
          (vlax-invoke-method sh 'Run cmd 0 :vlax-true)
          (vlax-release-object sh)
          (setq ok T)))))
  (if (not ok)
    (progn
      (startapp cmd)
      (getstring "\nΗ εντολή τρέχει σε παράθυρο cmd. Πατήστε Enter όταν ολοκληρωθεί... ")))
  T)

;; Επανακατασκευή polyline με νέες κορυφές
(defun dgm:rebuild (e pts closed / lay)
  (setq lay (cdr (assoc 8 (entget e))))
  (entdel e)
  (dgm:mkpoly pts lay closed))

;; Συλλογή LWPOLYLINES από layers: λίστα από (ename pts closed)
(defun dgm:collect (lays closedonly / ss i e out)
  (setq out nil)
  (foreach lay lays
    (setq ss (ssget "_X" (list '(0 . "LWPOLYLINE") (cons 8 lay))))
    (if ss
      (progn
        (setq i 0)
        (while (< i (sslength ss))
          (setq e (ssname ss i))
          (if (or (not closedonly) (dgm:closedp e))
            (setq out (cons (list e (dgm:lwpts e) (dgm:closedp e)) out)))
          (setq i (1+ i))))))
  out)

;; Off/επαναφορά layer
(defun dgm:layoff (nm / d)
  (setq d (entget (tblobjname "LAYER" nm)))
  (if d (entmod (subst (cons 62 (- (abs (cdr (assoc 62 d)))))
                       (assoc 62 d) d))))
(defun dgm:laycolor (nm col / d)
  (setq d (entget (tblobjname "LAYER" nm)))
  (if d (entmod (subst (cons 62 col) (assoc 62 d) d))))

;;; DGMCLEAN - Αυτόματος καθαρισμός τυπικών σφαλμάτων (τύπου KTM_CleanUp)
(defun dgm:cleangroup (items tol seed densifyp closep / allc pts new fix orig)
  (setq dgm:*canon* nil fix 0)
  (foreach p seed (dgm:canon p tol))
  (setq items
        (mapcar '(lambda (it)
                   (list (car it)
                         (mapcar '(lambda (p) (dgm:canon p tol)) (cadr it))
                         (caddr it)))
                items))
  (setq allc dgm:*canon*)
  (foreach it items
    (setq orig (dgm:lwpts (car it)))
    (setq pts (cadr it))
    (setq new (if densifyp (dgm:densify pts allc tol) pts))
    (setq new (dgm:dedup new))
    (if (or (not (equal new orig 1e-9))
            (and closep (not (caddr it))))
      (progn
        (dgm:rebuild (car it) new (if closep T (caddr it)))
        (setq fix (1+ fix)))))
  fix)

(defun c:DGMCLEAN ( / tol fix seedt seedn)
  (setq tol (dgm:getreal "\nΑνοχή καθαρισμού (m)" 0.001))
  (setq fix 0)
  ;; 1. PST_KAEK + DGM_PROP_FINAL: κλείσιμο, κούμπωμα κορυφών,
  ;;    προσθήκη κορυφών στα κοινά όρια, διαγραφή διπλών
  (setq fix (+ fix (dgm:cleangroup
                     (dgm:collect '("PST_KAEK" "DGM_PROP_FINAL") nil)
                     tol nil T T)))
  ;; κορυφές-στόχοι για τις επόμενες ομάδες
  (setq seedn nil)
  (foreach it (dgm:collect '("PST_KAEK" "DGM_PROP_FINAL") nil)
    (foreach p (cadr it) (setq seedn (cons p seedn))))
  ;; 2. AREA_A / AREA_D: κούμπωμα στα PST/DGM + διαγραφή διπλών
  (setq fix (+ fix (dgm:cleangroup (dgm:collect '("AREA_A" "AREA_D") nil)
                                   tol seedn nil nil)))
  ;; 3. BOUND_IMPL / BOUND_UNIMPL: κούμπωμα κορυφών
  (setq fix (+ fix (dgm:cleangroup (dgm:collect '("BOUND_IMPL" "BOUND_UNIMPL") nil)
                                   tol seedn nil nil)))
  ;; 4. VST / BLD / EAS: κούμπωμα στο TOPO_PROP
  (setq seedt nil)
  (foreach it (dgm:collect '("TOPO_PROP") nil)
    (foreach p (cadr it) (setq seedt (cons p seedt))))
  (setq fix (+ fix (dgm:cleangroup (dgm:collect '("VST" "BLD" "EAS") nil)
                                   tol seedt nil nil)))
  ;; 5. VST_FINAL / EAS_FINAL: κούμπωμα στο TOPO_PROP_NEW (αλλιώς TOPO_PROP)
  (setq seedn nil)
  (foreach it (dgm:collect '("TOPO_PROP_NEW") nil)
    (foreach p (cadr it) (setq seedn (cons p seedn))))
  (if (null seedn) (setq seedn seedt))
  (setq fix (+ fix (dgm:cleangroup (dgm:collect '("VST_FINAL" "EAS_FINAL") nil)
                                   tol seedn nil nil)))
  (princ (strcat "\nΚαθαρισμός ολοκληρώθηκε: διορθώθηκαν " (itoa fix)
                 " polylines."))
  (princ))

;;; DGMORIGIN - Αλλαγή αρχής και φοράς κλειστής polyline
(defun c:DGMORIGIN ( / en pts n p i bd best dir rot)
  (setq en (dgm:sel-poly "\nΕπιλέξτε κλειστή polyline: "))
  (cond
    ((null en))
    ((not (dgm:closedp en))
     (princ "\n** Η polyline δεν είναι κλειστή. **"))
    (t
     (setq pts (dgm:lwpts en) n (length pts))
     (setq p (getpoint "\nΕπιλέξτε τη νέα κορυφή αρχής: "))
     (if p
       (progn
         (setq p (list (car p) (cadr p)))
         (setq best 0 bd 1e99 i 0)
         (while (< i n)
           (if (< (distance p (nth i pts)) bd)
             (setq bd (distance p (nth i pts)) best i))
           (setq i (1+ i)))
         (princ "\nΦορά:  1 = CW (δεξιόστροφα)   2 = CCW (αριστερόστροφα)")
         (setq dir (dgm:getint "\nΕπιλογή" 1))
         (setq rot nil i 0)
         (while (< i n)
           (setq rot (append rot (list (nth (rem (+ best i) n) pts))))
           (setq i (1+ i)))
         (if (or (and (= dir 1) (> (dgm:sarea rot) 0))
                 (and (= dir 2) (< (dgm:sarea rot) 0)))
           (setq rot (cons (car rot) (reverse (cdr rot)))))
         (dgm:rebuild en rot T)
         (princ "\nΕνημερώθηκαν η αρχή και η φορά της polyline.")))))
  (princ))

;;; DGMBND / DGMBNDPD - Πολύγωνο από εσωτερικό σημείο (τύπου KTM_GetBoundary)
(defun dgm:boundary-core (lay / pt eb old cnt made)
  (dgm:layer-std lay)
  (setq old (getvar "CLAYER"))
  (setvar "CLAYER" lay)
  (setq cnt 0 made nil)
  (setq pt (getpoint "\nΕπιλέξτε εσωτερικό σημείο (Enter για τέλος): "))
  (while pt
    (setq eb (entlast))
    (command "_.-BOUNDARY" pt "")
    (if (not (eq eb (entlast)))
      (progn
        (setq cnt (1+ cnt))
        (setq made (cons (entlast) made)))
      (princ "\n** Δεν δημιουργήθηκε πολύγωνο στο σημείο αυτό. **"))
    (setq pt (getpoint "\nΕπόμενο εσωτερικό σημείο (Enter για τέλος): ")))
  (setvar "CLAYER" old)
  (princ (strcat "\nΔημιουργήθηκαν " (itoa cnt) " πολύγωνα στο layer " lay "."))
  made)

(defun c:DGMBND ( / lay made ans polys loops)
  (setq lay (dgm:getstr "\nLayer αποτελέσματος" "DGM_PROP_FINAL"))
  (setq made (dgm:boundary-core lay))
  (if (> (length made) 1)
    (progn
      (princ "\nΣυνένωση των πολυγώνων που δημιουργήθηκαν;  1 = Όχι   2 = Ναι")
      (setq ans (dgm:getint "\nΕπιλογή" 1))
      (if (= ans 2)
        (progn
          (setq polys (mapcar 'dgm:lwpts made))
          (setq loops (dgm:xorloops polys 0.001))
          (if (= 1 (length loops))
            (progn
              (foreach e made (entdel e))
              (dgm:mkpoly (car loops) lay T)
              (princ "\nΈγινε συνένωση σε ενιαίο πολύγωνο."))
            (princ "\n** Τα πολύγωνα δεν είναι όμορα - δεν έγινε συνένωση. **"))))))
  (princ))

(defun c:DGMBNDPD ( / states l nm)
  (dgm:layer-std "PST_KAEK")
  (dgm:layer-std "DGM_PROP_FINAL")
  (setq states nil)
  (setq l (tblnext "LAYER" T))
  (while l
    (setq nm (cdr (assoc 2 l)))
    (setq states (cons (cons nm (cdr (assoc 62 l))) states))
    (if (and (/= nm "PST_KAEK") (/= nm "DGM_PROP_FINAL"))
      (dgm:layoff nm))
    (setq l (tblnext "LAYER")))
  (dgm:boundary-core "DGM_PROP_FINAL")
  (foreach s states (dgm:laycolor (car s) (cdr s)))
  (princ))

;;; DGMKAT / DGMVST - Υποδιαίρεση πολυγώνων με γραμμές κοπής
(defun dgm:katcore (srclays cutlay outlay tol
                    / cuts work lpts item res newwork found cnt mp fin)
  (setq cuts (dgm:collect (list cutlay) nil))
  (setq work nil)
  (foreach item (dgm:collect srclays nil)
    (if (caddr item)
      (setq work (cons (list (cadr item) nil) work))))
  (cond
    ((null cuts)
     (princ (strcat "\n** Δεν βρέθηκαν γραμμές στο layer " cutlay ". **")))
    ((null work)
     (princ "\n** Δεν βρέθηκαν κλειστά πολύγωνα πηγής. **"))
    (t
     (setq cnt 0)
     (foreach ln cuts
       (setq lpts (cadr ln) found nil newwork nil)
       (setq mp (if (> (length lpts) 2)
                  (nth (/ (length lpts) 2) lpts)
                  (list (/ (+ (car (car lpts)) (car (last lpts))) 2.0)
                        (/ (+ (cadr (car lpts)) (cadr (last lpts))) 2.0))))
       (foreach item work
         (if (and (not found)
                  (dgm:onboundary (car lpts) (car item) tol)
                  (dgm:onboundary (last lpts) (car item) tol)
                  (dgm:inpoly mp (car item)))
           (progn
             (setq res (dgm:splitchord (car item) lpts tol))
             (if res
               (progn
                 (setq newwork (cons (list (car res) T)
                                     (cons (list (cadr res) T) newwork)))
                 (setq found T cnt (1+ cnt)))
               (setq newwork (cons item newwork))))
           (setq newwork (cons item newwork))))
       (setq work newwork)
       (if (not found)
         (progn
           (princ "\n[ΠΡΟΣΟΧΗ] Γραμμή κοπής χωρίς αντιστοίχιση: τα άκρα της πρέπει")
           (princ "\n          να ακουμπούν στο περίγραμμα πολυγώνου πηγής."))))
     (dgm:layer-std outlay)
     (setq fin 0)
     (foreach item work
       (if (cadr item)
         (progn
           (dgm:mkpoly (car item) outlay T)
           (setq fin (1+ fin)))))
     (princ (strcat "\nΕκτελέστηκαν " (itoa cnt) " κοπές - δημιουργήθηκαν "
                    (itoa fin) " πολύγωνα στο layer " outlay ".")))))

(defun c:DGMKAT ( / tol)
  (setq tol (dgm:getreal "\nΑνοχή (m)" 0.001))
  (dgm:katcore '("PST_KAEK") "LINE_XM" "DGM_PROP_FINAL" tol)
  (princ "\nΥπενθύμιση: τοποθετήστε κείμενα ΝΕΟ ... (layer PST_KAEK) στα νέα πολύγωνα.")
  (princ))

(defun c:DGMVST ( / tol)
  (setq tol (dgm:getreal "\nΑνοχή (m)" 0.001))
  (dgm:katcore '("PST_KAEK" "DGM_PROP_FINAL") "LINE_XM_VST" "VST_FINAL" tol)
  (princ))

;;; DGMGM - Τελικά όρια (DGM_PROP_FINAL) των επηρεαζόμενων ομόρων PST_KAEK,
;;; ως προς το δικό μας γεωτεμάχιο (DGMOUR). Από κάθε όμορο αφαιρούνται τα
;;; διεκδικούμενα τμήματα και του προστίθενται τα αποκοπτόμενα.
(defun c:DGMGM ( / our n)
  (setq our (dgm:our))
  (if (null our)
    (if (dgm:pick-our) (setq our (dgm:our))))
  (cond
    ((null our)
     (princ "\n** Δεν ορίστηκε το δικό μας γεωτεμάχιο (DGMOUR). **"))
    ((> (length (dgm:collect '("DGM_PROP_FINAL") T)) 1)
     (princ "\n** Υπάρχουν ήδη και άλλα DGM_PROP_FINAL εκτός του δικού μας - σβήστε τα για επαναδημιουργία. **"))
    (t
     (setq n (dgm:geo-core (cadr (cadr our)) (cadr (car our))
                           (dgm:otherpst (car (cadr our)))
                           0.001 dgm:*h* 0.01 nil T))
     (princ (strcat "\nΔημιουργήθηκαν " (itoa (caddr n))
                    " πολύγωνα DGM_PROP_FINAL επηρεαζόμενων ομόρων."))))
  (princ))

;;; DGMAREAS - Αυτόματη δημιουργία AREA_A/AREA_D (KTM_CreateAreas)
(defun dgm:countlabels (lay / ss)
  (setq ss (ssget "_X" (list '(0 . "TEXT,MTEXT") (cons 8 lay))))
  (if ss (sslength ss) 0))

;; Το μικρότερο κλειστό πολύγωνο των layers lays που περιέχει το σημείο pt.
;; Επιστρέφει (ename pts closed) ή nil.
(defun dgm:polyat (pt lays / best ba a)
  (foreach it (dgm:collect lays T)
    (if (dgm:inpoly pt (cadr it))
      (progn
        (setq a (abs (dgm:area (cadr it))))
        (if (or (null best) (< a ba)) (setq best it ba a)))))
  best)

;; Θέση ετικέτας πολυγώνου: το εσωτερικό σημείο που απέχει περισσότερο από
;; το περίγραμμα (κεντροειδές + κάναβος 9x9 στο περιβάλλον ορθογώνιο), ώστε
;; το κείμενο να μην πέφτει πάνω στις γραμμές. Επιστρέφει (σημείο . απόσταση).
(defun dgm:labelpt (pts / x0 x1 y0 y1 best bd c q d i j)
  (setq x0 (apply 'min (mapcar 'car pts))  x1 (apply 'max (mapcar 'car pts))
        y0 (apply 'min (mapcar 'cadr pts)) y1 (apply 'max (mapcar 'cadr pts))
        best nil bd -1.0)
  (setq c (dgm:centroid pts))
  (if (and c (dgm:inpoly c pts))
    (setq best c bd (dgm:pmindist c pts)))
  (setq i 1)
  (while (< i 10)
    (setq j 1)
    (while (< j 10)
      (setq q (list (+ x0 (* (- x1 x0) (/ i 10.0)))
                    (+ y0 (* (- y1 y0) (/ j 10.0)))))
      (if (dgm:inpoly q pts)
        (progn
          (setq d (dgm:pmindist q pts))
          (if (> d bd) (setq bd d best q))))
      (setq j (1+ j)))
    (setq i (1+ i)))
  (if (null best)
    (progn (setq best (dgm:innerpt pts))
           (setq bd (if best (dgm:pmindist best pts) 0.0))))
  (if best (cons best bd)))

;; Ετικέτα τμήματος στο "κέντρο" του πολυγώνου· σε στενά τμήματα το ύψος του
;; κειμένου μειώνεται (έως το μισό) ώστε να χωρά καλύτερα.
(defun dgm:arealabel (pts h nm lay / lp lh)
  (setq lp (dgm:labelpt pts))
  (if lp
    (progn
      (setq lh (max (* 0.5 h) (min h (* 1.5 (cdr lp)))))
      (dgm:textc (car lp) lh nm lay))))

;; Πλησιέστερο σημείο του τμήματος a-b προς το σημείο p
(defun dgm:segnear (p a b / dx dy l2 tp)
  (setq dx (- (car b) (car a)) dy (- (cadr b) (cadr a))
        l2 (+ (* dx dx) (* dy dy)))
  (if (< l2 1e-12)
    a
    (progn
      (setq tp (/ (+ (* (- (car p) (car a)) dx) (* (- (cadr p) (cadr a)) dy)) l2))
      (if (< tp 0.0) (setq tp 0.0))
      (if (> tp 1.0) (setq tp 1.0))
      (list (+ (car a) (* tp dx)) (+ (cadr a) (* tp dy))))))

;; Σημείο αυστηρά στο εσωτερικό πολυγώνου (όχι πάνω στο περίγραμμα)
(defun dgm:strictin (p pts tol)
  (and (dgm:inpoly p pts) (not (dgm:onboundary p pts tol))))

;; Αληθές αν κάποια κορυφή ή μέσο πλευράς του a είναι αυστηρά μέσα στο b
(defun dgm:anyin (a b tol / r n i p1 p2)
  (setq r nil n (length a) i 0)
  (while (and (< i n) (not r))
    (setq p1 (nth i a) p2 (nth (rem (1+ i) n) a))
    (if (or (dgm:strictin p1 b tol)
            (dgm:strictin (list (/ (+ (car p1) (car p2)) 2.0)
                                (/ (+ (cadr p1) (cadr p2)) 2.0))
                          b tol))
      (setq r T))
    (setq i (1+ i)))
  r)

;; Αληθές αν τα πολύγωνα a και b επικαλύπτονται (όχι απλή επαφή ορίων).
;; Ελέγχονται εσωτερικά σημεία, κορυφές ΚΑΙ μέσα πλευρών και των δύο, ώστε
;; να πιάνεται και η περίπτωση όπου το ένα κόβει το άλλο με χορδή (όλες οι
;; κορυφές πάνω στα περιγράμματα, καμία αυστηρά στο εσωτερικό).
(defun dgm:overlapp (a b tol / ia ib)
  (setq ia (dgm:innerpt a) ib (dgm:innerpt b))
  (or (and ia (dgm:inpoly ia b))
      (and ib (dgm:inpoly ib a))
      (dgm:anyin a b tol)
      (dgm:anyin b a tol)))

;; Διαχωρισμός αποκοπτόμενου τμήματος a ανά όμορο ΚΑΕΚ: όπου το κοινό όριο
;; δύο ομόρων συναντά το τμήμα, αυτό κόβεται προς το πλησιέστερο σημείο του
;; τελικού ορίου f. others = ((pts . kaek) ...). Επιστρέφει λίστα τμημάτων.
(defun dgm:splitA (a f others tol / allv adj pcs js q c dup j pc k bd np i
                     p1 p2 mp cc dd r)
  (setq allv nil)
  (foreach it others (foreach q (car it) (setq allv (cons q allv))))
  (setq a (dgm:dedup (dgm:densify a allv tol)))
  (setq adj nil)
  (foreach it others
    (if (> (dgm:sharedlen a (car it) tol) tol)
      (setq adj (cons (car it) adj))))
  (setq pcs (list a))
  (if (> (length adj) 1)
    (progn
      ;; σημεία όπου συναντώνται δύο όμοροι πάνω στο περίγραμμα του τμήματος
      (setq js nil)
      (foreach nb adj
        (foreach q nb
          (if (and (dgm:onboundary q a tol)
                   (>= (dgm:pmindist q f) tol))
            (progn
              (setq c 0 dup nil)
              (foreach m adj (if (dgm:onboundary q m tol) (setq c (1+ c))))
              (foreach j js (if (< (distance j q) tol) (setq dup T)))
              (if (and (>= c 2) (not dup)) (setq js (cons q js)))))))
      (foreach j js
        (setq pc nil)
        (foreach x pcs
          (if (and (null pc) (dgm:onboundary j x tol)) (setq pc x)))
        (if pc
          (progn
            (setq k nil bd 1e99 np (length pc) i 0)
            (while (< i np)
              (setq p1 (nth i pc) p2 (nth (rem (1+ i) np) pc)
                    mp (list (/ (+ (car p1) (car p2)) 2.0)
                             (/ (+ (cadr p1) (cadr p2)) 2.0)))
              (if (< (dgm:pmindist mp f) tol)
                (progn
                  (setq cc (dgm:segnear j p1 p2) dd (distance j cc))
                  (if (and (> dd tol) (< dd bd)) (setq bd dd k cc))))
              (setq i (1+ i)))
            (if k
              (progn
                (setq r (dgm:splitchord pc (list j k) tol))
                (if r (setq pcs (append r (dgm:rm pc pcs)))))))))))
  pcs)

;; Πυρήνας γεωμετρίας διόρθωσης ως προς το ΔΙΚΟ ΜΑΣ γεωτεμάχιο.
;; p = αρχικό όριό μας (PST_KAEK), f = τελικό όριό μας (DGM_PROP_FINAL),
;; others = ((pts . kaek) ...) τα υπόλοιπα PST_KAEK.
;; - Τμήματα Δ (διεκδικούμενα, εντός f εκτός p) και Α (αποκοπτόμενα, εντός p
;;   εκτός f), ΔΙΑΧΩΡΙΣΜΕΝΑ ανά επηρεαζόμενο PST_KAEK.
;; - mkareas: δημιουργία πολυγώνων AREA_A / AREA_D με ετικέτες.
;; - mkneigh: δημιουργία DGM_PROP_FINAL των επηρεαζόμενων ομόρων (αφαίρεση
;;   των Δ που πέφτουν μέσα τους, προσθήκη των Α που συνορεύουν μαζί τους).
;; Επιστρέφει (πλήθος-Α πλήθος-Δ πλήθος-ομόρων).
(defun dgm:geo-core (p f others tol h minw mkareas mkneigh
                     / al dl loop ip inp ind w ar items it pcs npcs pc chg d l q
                       rmn dparts dfin aparts sum a best bl s bj bs m
                       na nd nm cnt cn)
  ;; 1. ταξινόμηση βρόχων XOR(p,f)
  (setq al nil dl nil)
  (foreach loop (dgm:xorloops (list p f) tol)
    (setq ar (dgm:area loop)
          w (if (> (dgm:perim loop) 1e-9) (/ (* 2.0 ar) (dgm:perim loop)) 0.0)
          ip (dgm:innerpt loop))
    (cond
      ((< w minw)
       (princ (strcat "\n[INFO] Παραλείφθηκε τμήμα με πλάτος "
                      (rtos w 2 3) " m (όριο " (rtos minw 2 3) " m).")))
      ((null ip) nil)
      (t
       (setq inp (dgm:inpoly ip p) ind (dgm:inpoly ip f))
       (cond ((and inp (not ind)) (setq al (cons loop al)))
             ((and ind (not inp)) (setq dl (cons loop dl)))))))
  ;; 2. τα Δ ανά όμορο: τομή με κάθε PST_KAEK και αφαίρεσή της από αυτό
  (setq items nil dparts nil)
  (foreach it others
    (setq pcs (list (car it)) chg nil)
    (foreach d dl
      (setq npcs nil)
      (foreach pc pcs
        (if (dgm:overlapp d pc tol)
          (progn
            (setq rmn nil)
            (foreach l (dgm:xorloops (list pc d) tol)
              (setq q (dgm:innerpt l))
              (if (and q (dgm:inpoly q pc) (not (dgm:inpoly q d))
                       (< (dgm:area l) (- (dgm:area pc) 1e-9)))
                (setq rmn (cons l rmn))))
            (if rmn
              (foreach l (dgm:xorloops (cons pc rmn) tol)
                (setq q (dgm:innerpt l))
                (if (and q (dgm:inpoly q d) (dgm:inpoly q pc))
                  (setq dparts (cons (cons d l) dparts))))
              (setq dparts (cons (cons d pc) dparts)))
            (setq chg T npcs (append rmn npcs)))
          (setq npcs (cons pc npcs))))
      (setq pcs npcs))
    (setq items (cons (list (car it) pcs chg (cdr it)) items)))
  ;; τελικά τμήματα Δ (όσα δεν πέφτουν σε κανένα PST_KAEK μένουν ενιαία)
  (setq dfin nil)
  (foreach d dl
    (setq sum 0.0 cn 0)
    (foreach x dparts
      (if (eq (car x) d)
        (setq dfin (cons (cdr x) dfin)
              sum (+ sum (dgm:area (cdr x))) cn (1+ cn))))
    (cond
      ((= cn 0) (setq dfin (cons d dfin)))
      ((< sum (- (dgm:area d) 0.01))
       (princ (strcat "\n[ΠΡΟΣΟΧΗ] Μέρος διεκδικούμενου τμήματος ("
                      (rtos (- (dgm:area d) sum) 2 2)
                      " τ.μ.) δεν ανήκει σε κανένα PST_KAEK - ελέγξτε.")))))
  ;; 3. τα Α ανά όμορο
  (setq aparts nil)
  (foreach a al
    (setq aparts (append (dgm:splitA a f others tol) aparts)))
  ;; 4. πολύγωνα AREA_A / AREA_D με ετικέτες
  (if mkareas
    (progn
      (dgm:layer-std "AREA_A")
      (dgm:layer-std "AREA_D")
      (dgm:layer-std "AREA_A-labels")
      (dgm:layer-std "AREA_D-labels")
      (setq na (1+ (dgm:countlabels "AREA_A-labels"))
            nd (1+ (dgm:countlabels "AREA_D-labels")))
      (foreach a aparts
        (setq nm (strcat "ΤΜΗΜΑ Α" (itoa na)) na (1+ na))
        (dgm:mkpoly a "AREA_A" T)
        (dgm:arealabel a h nm "AREA_A-labels")
        (princ (strcat "\n    " nm " (αποκοπτόμενο): "
                       (rtos (dgm:area a) 2 2) " τ.μ.")))
      (foreach d dfin
        (setq nm (strcat "ΤΜΗΜΑ Δ" (itoa nd)) nd (1+ nd))
        (dgm:mkpoly d "AREA_D" T)
        (dgm:arealabel d h nm "AREA_D-labels")
        (princ (strcat "\n    " nm " (διεκδικούμενο): "
                       (rtos (dgm:area d) 2 2) " τ.μ.")))))
  ;; 5. τελικά όρια επηρεαζόμενων ομόρων
  (setq cnt 0)
  (if mkneigh
    (progn
      (foreach a aparts
        (setq best nil bl tol)
        (foreach it items
          (setq s (dgm:sharedlen a (car it) tol))
          (if (> s bl) (setq bl s best it)))
        (if (null best)
          (princ "\n[INFO] Αποκοπτόμενο τμήμα χωρίς όμορο PST_KAEK - δεν αποδόθηκε σε γεωτεμάχιο.")
          (progn
            (setq bj nil bs -1.0)
            (foreach pc (cadr best)
              (setq s (dgm:sharedlen a pc tol))
              (if (> s bs) (setq bs s bj pc)))
            (setq m (if bj (dgm:xorloops (list bj a) tol)))
            (if (and m (= 1 (length m)))
              (setq items (subst (list (car best) (subst (car m) bj (cadr best))
                                       T (cadddr best))
                                 best items))
              (princ "\n[ΠΡΟΣΟΧΗ] Αποτυχία συνένωσης αποκοπτόμενου τμήματος με τον όμορο - ελέγξτε χειροκίνητα.")))))
      (dgm:layer-std "DGM_PROP_FINAL")
      (foreach it items
        (if (and (caddr it) (> (length (cadr it)) 1))
          (princ (strcat "\n[ΠΡΟΣΟΧΗ] Το ΚΑΕΚ "
                         (if (cadddr it) (cadddr it) "(χωρίς κείμενο)")
                         " χωρίζεται σε " (itoa (length (cadr it)))
                         " τμήματα από το τελικό μας όριο - ελέγξτε.")))
        (if (caddr it)
          (foreach pc (cadr it)
            (dgm:mkpoly pc "DGM_PROP_FINAL" T)
            (setq cnt (1+ cnt))
            (princ (strcat "\n    Τελικό όριο ΚΑΕΚ "
                           (if (cadddr it) (cadddr it) "(χωρίς κείμενο)") ": "
                           (rtos (dgm:area (car it)) 2 2) " -> "
                           (rtos (dgm:area pc) 2 2) " τ.μ.")))))))
  (list (length aparts) (length dfin) cnt))

;; Τα υπόλοιπα κλειστά PST_KAEK (εκτός του ename ex) ως ((pts . kaek) ...)
(defun dgm:otherpst (ex / out ktexts)
  (setq out nil ktexts (dgm:kaektexts))
  (foreach it (dgm:collect '("PST_KAEK") T)
    (if (not (eq (car it) ex))
      (setq out (cons (cons (cadr it) (dgm:kaekof (cadr it) ktexts)) out))))
  out)

;; Η εντολή ρωτά ΠΡΩΤΑ ποιο γεωτεμάχιο είναι το δικό μας (σημείο στο εσωτερικό
;; του) και μετά καθορίζει τα AREA_A / AREA_D ως προς αυτό.
(defun c:DGMAREAS ( / pt it tol h minw e1 e2 kaek)
  (setq pt (getpoint (strcat "\nΔείξτε σημείο ΜΕΣΑ στο ΔΙΚΟ ΜΑΣ γεωτεμάχιο "
                             "(Enter = επιλογή των πολυγώνων): ")))
  (if pt
    (progn
      (setq pt (list (car pt) (cadr pt)))
      (if (setq it (dgm:polyat pt '("PST_KAEK"))) (setq e1 (car it)))
      (if (setq it (dgm:polyat pt '("DGM_PROP_FINAL"))) (setq e2 (car it)))))
  (if (null e1)
    (setq e1 (dgm:sel-poly "\nΕπιλέξτε το πολύγωνο PST_KAEK του δικού μας γεωτεμαχίου: ")))
  (if (and e1 (null e2))
    (setq e2 (dgm:sel-poly "\nΕπιλέξτε το πολύγωνο DGM_PROP_FINAL του δικού μας γεωτεμαχίου: ")))
  (if (and e1 e2)
    (if (or (not (dgm:closedp e1)) (not (dgm:closedp e2)))
      (princ "\n** Και τα δύο πολύγωνα πρέπει να είναι κλειστά. **")
      (progn
        (setq kaek (dgm:kaekof (dgm:lwpts e1) (dgm:kaektexts)))
        (princ (strcat "\nΔικό μας γεωτεμάχιο: ΚΑΕΚ " (if kaek kaek "(χωρίς κείμενο ΚΑΕΚ)")))
        (setq tol (dgm:getreal "\nΑνοχή (m)" 0.001))
        (setq h (dgm:getreal "\nΎψος χαρακτήρων ετικετών" dgm:*h*))
        (setq dgm:*h* h)
        (setq minw (dgm:getreal "\nΔιαγραφή πολυγώνων με πλάτος <" 0.01))
        (dgm:geo-core (dgm:lwpts e1) (dgm:lwpts e2) (dgm:otherpst e1)
                      tol h minw T nil)
        (princ "\nΟλοκληρώθηκε η δημιουργία AREA_A/AREA_D."))))
  (princ))

;;; DGMGEO - Γεωμετρία του ΔΓΜ σε ΕΝΑ βήμα.
;;; Διόρθωση ορίων: για το δικό μας γεωτεμάχιο (DGMOUR) δημιουργεί τα
;;; AREA_A/AREA_D και τα DGM_PROP_FINAL των επηρεαζόμενων ομόρων.
;;; Πράξη: καθαρισμός, κατάτμηση PST_KAEK με LINE_XM, έλεγχος ορθότητας.

;; Εκτέλεση άλλης εντολής DGM μέσα από σύνθετη εντολή (χωρίς νέα ομάδα UNDO)
(defun dgm:call (nm / f)
  (setq f (eval (read (strcat "DGM:ORIG-" nm))))
  (if (null f) (setq f (eval (read (strcat "C:" nm)))))
  (if f (apply f nil)))

;; Το ίδιο, με σιωπηλή αποδοχή όλων των προεπιλεγμένων απαντήσεων
(defun dgm:callauto (nm)
  (setq dgm:*auto* T)
  (dgm:call nm)
  (setq dgm:*auto* nil))

(defun dgm:plcount (flt / ss)
  (setq ss (ssget "_X" (list '(0 . "LWPOLYLINE") (cons 8 flt))))
  (if ss (sslength ss) 0))

;;; DGMOUR - Επιλογή της polyline DGM_PROP_FINAL του ΔΙΚΟΥ ΜΑΣ γεωτεμαχίου.
;;; Η επιλογή απομνημονεύεται (ως εσωτερικά σημεία των δύο πολυγώνων) και
;;; χρησιμοποιείται από την DGMGEO.
(defun dgm:pick-our ( / en lay pts ip ex pst kaek ok e2)
  (setq en (dgm:sel-poly "\nΕπιλέξτε την polyline DGM_PROP_FINAL του ΔΙΚΟΥ ΜΑΣ γεωτεμαχίου: "))
  (setq ok nil)
  (cond
    ((null en) nil)
    ((not (dgm:closedp en))
     (princ "\n** Η polyline πρέπει να είναι κλειστή. **"))
    (t
     (setq lay (cdr (assoc 8 (entget en)))
           pts (dgm:lwpts en)
           ip (dgm:innerpt pts))
     (if (/= (strcase lay) "DGM_PROP_FINAL")
       (progn
         ;; ίσως επιλέχθηκε συμπίπτουσα polyline άλλου layer (π.χ. TOPO_PROP)
         (setq ex (if ip (dgm:polyat ip '("DGM_PROP_FINAL"))))
         (if (and ex (< (abs (- (dgm:area (cadr ex)) (dgm:area pts))) 0.01))
           (setq en (car ex) pts (cadr ex))
           (progn
             (princ (strcat "\nΗ polyline είναι στο layer " lay
                            ".  1 = Αντιγραφή της στο DGM_PROP_FINAL   0 = Άκυρο"))
             (if (= 1 (dgm:getint "\nΕπιλογή" 1))
               (progn
                 (dgm:layer-std "DGM_PROP_FINAL")
                 (dgm:mkpoly pts "DGM_PROP_FINAL" T))
               (setq en nil))))))
     (if (and en ip)
       (progn
         ;; το αρχικό μας γεωτεμάχιο (PST_KAEK)
         (setq pst (dgm:polyat ip '("PST_KAEK")))
         (if pst
           (progn
             (setq kaek (dgm:kaekof (cadr pst) (dgm:kaektexts)))
             (princ (strcat "\nΑρχικό μας γεωτεμάχιο: ΚΑΕΚ "
                            (if kaek kaek "(χωρίς κείμενο ΚΑΕΚ)") ", "
                            (rtos (dgm:area (cadr pst)) 2 2) " τ.μ."
                            "   Σωστό;  1 = Ναι   0 = Όχι (επιλογή πολυγώνου)"))
             (if (/= 1 (dgm:getint "\nΕπιλογή" 1)) (setq pst nil))))
         (if (null pst)
           (progn
             (setq e2 (dgm:sel-poly "\nΕπιλέξτε το πολύγωνο PST_KAEK (αρχικό) του δικού μας γεωτεμαχίου: "))
             (if (and e2 (dgm:closedp e2))
               (setq pst (list e2 (dgm:lwpts e2) T)))))
         (if pst
           (progn
             (setq dgm:*our-fin* ip
                   dgm:*our-pst* (dgm:innerpt (cadr pst)))
             (princ (strcat "\nΟρίστηκε το δικό μας γεωτεμάχιο: αρχικό "
                            (rtos (dgm:area (cadr pst)) 2 2) " τ.μ., τελικό "
                            (rtos (dgm:area pts) 2 2) " τ.μ."))
             (setq ok T))
           (princ "\n** Δεν ορίστηκε το αρχικό PST_KAEK. **"))))))
  ok)

(defun c:DGMOUR ()
  (if (dgm:pick-our)
    (princ "\nΕπόμενο βήμα: DGMGEO (τελικά όρια ομόρων + AREA_A/AREA_D)."))
  (princ))

;; Το δικό μας γεωτεμάχιο όπως ορίστηκε με την DGMOUR: (τελικό αρχικό) ή nil
(defun dgm:our ( / fin pst)
  (if (and dgm:*our-fin* dgm:*our-pst*)
    (progn
      (setq fin (dgm:polyat dgm:*our-fin* '("DGM_PROP_FINAL"))
            pst (dgm:polyat dgm:*our-pst* '("PST_KAEK")))
      (if (and fin pst) (list fin pst)))))

;; Διόρθωση ορίων: δημιουργεί ΜΟΝΟ τα AREA_A/AREA_D και τα τελικά όρια
;; (DGM_PROP_FINAL) των επηρεαζόμενων ομόρων. Το δικό μας DGM_PROP_FINAL
;; δεν δημιουργείται εδώ - επιλέγεται με την DGMOUR.
(defun dgm:geo-dior (h / our fin pst kaek ktexts n mka mkn)
  (setq our (dgm:our))
  (if (null our)
    (if (dgm:pick-our) (setq our (dgm:our))))
  (if (null our)
    (princ "\n** Δεν ορίστηκε το δικό μας γεωτεμάχιο - εκτελέστε πρώτα την DGMOUR. **")
    (progn
      (setq fin (car our) pst (cadr our)
            ktexts (dgm:kaektexts)
            kaek (dgm:kaekof (cadr pst) ktexts))
      (princ (strcat "\nΔικό μας γεωτεμάχιο: ΚΑΕΚ "
                     (if kaek kaek "(χωρίς κείμενο ΚΑΕΚ)")
                     ", αρχικό " (rtos (dgm:area (cadr pst)) 2 2)
                     " τ.μ., τελικό " (rtos (dgm:area (cadr fin)) 2 2) " τ.μ."))
      (setq mka (= 0 (dgm:plcount "AREA_A,AREA_D"))
            mkn (<= (length (dgm:collect '("DGM_PROP_FINAL") T)) 1))
      (if (not mka)
        (princ "\n[!] Υπάρχουν ήδη πολύγωνα AREA_A/AREA_D - δεν ξαναδημιουργήθηκαν."))
      (if (not mkn)
        (princ "\n[!] Υπάρχουν ήδη και άλλα DGM_PROP_FINAL - τα όρια των ομόρων δεν ξαναδημιουργήθηκαν."))
      (if (or mka mkn)
        (progn
          (princ "\nΤμήματα Α/Δ ανά επηρεαζόμενο ΚΑΕΚ και τελικά όρια ομόρων:")
          (setq n (dgm:geo-core (cadr pst) (cadr fin) (dgm:otherpst (car pst))
                                0.001 h 0.01 mka mkn))
          (princ (strcat "\nΣύνολο: " (itoa (car n)) " τμήματα Α, "
                         (itoa (cadr n)) " τμήματα Δ"
                         (if mkn (strcat ", " (itoa (caddr n))
                                         " πολύγωνα DGM_PROP_FINAL ομόρων") "")
                         "."))))
      (princ "\nΕπόμενα βήματα: DGMC (έλεγχος) και DGMAUTO (αρίθμηση + πίνακες).")))
  (princ))

(defun dgm:geo-praksi ( / gm nx nd fl)
  (princ "\nΑντιγραφή και των αμετάβλητων ΚΑΕΚ στο DGM_PROP_FINAL;  1 = Ναι   0 = Όχι")
  (setq gm (dgm:getint "\nΕπιλογή" 0))
  (princ "\n[1] Καθαρισμός...")
  (dgm:callauto "DGMCLEAN")
  (setq nx (length (dgm:collect '("LINE_XM") nil))
        nd (length (dgm:collect '("DGM_PROP_FINAL") T)))
  (cond
    ((> nd 0)
     (princ "\n[2] Υπάρχουν ήδη πολύγωνα DGM_PROP_FINAL - η κατάτμηση δεν επαναλήφθηκε."))
    ((> nx 0)
     (princ "\n[2] Κατάτμηση PST_KAEK με τις γραμμές LINE_XM:")
     (dgm:katcore '("PST_KAEK") "LINE_XM" "DGM_PROP_FINAL" 0.001)
     (princ "\n    Υπενθύμιση: τοποθετήστε κείμενα ΝΕΟ ... (layer PST_KAEK) στα νέα πολύγωνα."))
    (t
     (princ "\n[2] Δεν υπάρχουν γραμμές κατάτμησης στο LINE_XM. Για συνένωση: DGMUNION.")))
  (if (and (= gm 1) (> (length (dgm:collect '("DGM_PROP_FINAL") T)) 0))
    (progn
      (princ "\n[3] Αμετάβλητα ΚΑΕΚ:")
      (setq nx 0 fl (dgm:collect '("DGM_PROP_FINAL") T))
      (foreach it (dgm:collect '("PST_KAEK") T)
        (setq nd nil)
        (foreach g fl
          (if (dgm:overlapp (cadr it) (cadr g) 0.001) (setq nd T)))
        (if (not nd)
          (progn (dgm:mkpoly (cadr it) "DGM_PROP_FINAL" T) (setq nx (1+ nx)))))
      (princ (strcat " αντιγράφηκαν " (itoa nx) " στο DGM_PROP_FINAL."))))
  (dgm:callauto "DGMCLEAN")
  (princ "\n[4] Έλεγχος ορθότητας:")
  (dgm:callauto "DGMC")
  (princ "\nΕπόμενο βήμα: DGMAUTO (αρίθμηση κορυφών + όλοι οι πίνακες).")
  (princ))

(defun c:DGMGEO ( / typ h)
  (princ "\nΓεωμετρία ΔΓΜ σε ένα βήμα:  2 = Διόρθωση ορίων   3 = Πράξη (κατάτμηση)")
  (setq typ (dgm:getint "\nΕπιλογή" (if (= dgm:*typ* 3) 3 2)))
  (if (/= typ 3) (setq typ 2))
  (setq dgm:*typ* typ)
  (if (= typ 3)
    (dgm:geo-praksi)
    (progn
      (setq h (dgm:getreal "\nΎψος χαρακτήρων ετικετών τμημάτων" dgm:*h*))
      (setq dgm:*h* h)
      (dgm:geo-dior h)))
  (princ))

;;; DGMCOPY - Αντιγραφή γραμμών TOPO_PROP σε άλλα layers
(defun c:DGMCOPY ( / typ src dst ss i e cnt)
  (princ "\nΑντιγραφή όλων των γραμμών TOPO_PROP σε:")
  (princ "\n  1 = DGM_PROP_FINAL   2 = BOUND_IMPL   3 = BOUND_UNIMPL")
  (setq typ (dgm:getint "\nΕπιλογή" 1))
  (setq src "TOPO_PROP"
        dst (cond ((= typ 2) "BOUND_IMPL")
                  ((= typ 3) "BOUND_UNIMPL")
                  (t "DGM_PROP_FINAL")))
  (dgm:layer-std dst)
  (setq ss (ssget "_X" (list '(0 . "LWPOLYLINE") (cons 8 src)))
        cnt 0)
  (if ss
    (progn
      (setq i 0)
      (while (< i (sslength ss))
        (setq e (ssname ss i))
        (dgm:mkpoly (dgm:lwpts e) dst (dgm:closedp e))
        (setq cnt (1+ cnt))
        (setq i (1+ i)))))
  (princ (strcat "\nΑντιγράφηκαν " (itoa cnt) " polylines από " src
                 " στο " dst "."))
  (princ))

;;; DGMTXT - Εξαγωγή συντεταγμένων κορυφών σε αρχείο TXT
(defun c:DGMTXT ( / f fn ss i e pts h nn)
  (princ "\nΕξαγωγή συντεταγμένων κορυφών επιλεγμένων polylines σε αρχείο TXT.")
  (setq ss (ssget '((0 . "LWPOLYLINE"))))
  (if ss
    (progn
      (setq fn (getfiled "Αποθήκευση συντεταγμένων" "" "txt" 1))
      (if fn
        (progn
          (setq f (open fn "w"))
          (dgm:marks-load)
          (setq h (if dgm:*h* dgm:*h* 0.5))
          (setq i 0)
          (while (< i (sslength ss))
            (setq e (ssname ss i)
                  pts (dgm:lwpts e))
            (foreach p pts
              (setq nn (dgm:findnum p dgm:*findtol*))
              (write-line (strcat (if nn nn "-") "\t"
                                  (rtos (car p) 2 3) "\t"
                                  (rtos (cadr p) 2 3))
                          f))
            (setq i (1+ i)))
          (close f)
          (princ (strcat "\nΓράφτηκε το αρχείο: " fn))))))
  (princ))

;;; DGMPREP - Προετοιμασία σχεδίου για υποβολή (KTM_PrepareDwg)
(defun dgm:hasxref ( / b r)
  (setq b (tblnext "BLOCK" T) r nil)
  (while b
    (if (= 4 (logand 4 (cdr (assoc 70 b)))) (setq r T))
    (setq b (tblnext "BLOCK")))
  r)

(defun dgm:delall (etype / ss i cnt)
  (setq ss (ssget "_X" (list (cons 0 etype))) cnt 0)
  (if ss
    (progn
      (setq i 0)
      (while (< i (sslength ss))
        (entdel (ssname ss i))
        (setq cnt (1+ cnt) i (1+ i)))))
  cnt)

(defun c:DGMPREP ( / a1 a2 a3 a4 ax ss i n)
  (princ "\nΠροετοιμασία σχεδίου για υποβολή (1 = Ναι, 0 = Όχι):")
  (setq a1 (dgm:getint "\nΔιαγραφή εικόνων (Images)" 1))
  (setq a2 (dgm:getint "\nΔιάλυση blocks (Explode)" 1))
  (setq a3 (dgm:getint "\nΔιαγραφή αντικειμένων OLE" 1))
  (setq a4 (dgm:getint "\nΔιαγραφή Proxy entities" 1))
  (princ "\nXrefs:  0 = καμία ενέργεια   1 = Detach όλα   2 = Bind όλα")
  (setq ax (dgm:getint "\nΕπιλογή" 1))
  (if (= a1 1)
    (princ (strcat "\nΔιαγράφηκαν " (itoa (dgm:delall "IMAGE")) " εικόνες.")))
  (if (= a3 1)
    (princ (strcat "\nΔιαγράφηκαν " (itoa (dgm:delall "OLE2FRAME")) " OLE.")))
  (if (= a4 1)
    (princ (strcat "\nΔιαγράφηκαν "
                   (itoa (dgm:delall "ACAD_PROXY_ENTITY")) " proxies.")))
  (if (= a2 1)
    (progn
      (setq n 0)
      (setq ss (ssget "_X" '((0 . "INSERT"))))
      (while (and ss (< n 5))
        (setq i 0)
        (while (< i (sslength ss))
          (command "_.EXPLODE" (ssname ss i))
          (setq i (1+ i)))
        (setq n (1+ n))
        (setq ss (ssget "_X" '((0 . "INSERT")))))
      (princ "\nΈγινε διάλυση των blocks.")))
  (if (and (/= ax 0) (dgm:hasxref))
    (if (= ax 2)
      (command "_.-XREF" "_B" "*")
      (command "_.-XREF" "_D" "*")))
  (princ "\nΗ προετοιμασία ολοκληρώθηκε. Εκτελέστε DGMC για τελικό έλεγχο.")
  (princ))

;;; DGMZIP - Δημιουργία ZIP παραδοτέων (DXF + υπογεγραμμένο PDF)
(defun c:DGMZIP ( / dxf pdf zip cmd)
  (setq dxf (getfiled "Επιλογή αρχείου DXF" "" "dxf" 0))
  (setq pdf (if dxf (getfiled "Επιλογή υπογεγραμμένου PDF" "" "pdf" 0)))
  (if (and dxf pdf)
    (progn
      (setq zip (strcat (substr dxf 1 (- (strlen dxf) 4)) ".zip"))
      (setq cmd (strcat "powershell -NoProfile -Command \"Compress-Archive -Force -LiteralPath '"
                        dxf "','" pdf "' -DestinationPath '" zip "'\""))
      (dgm:runsync cmd)
      (if (findfile zip)
        (princ (strcat "\nΔημιουργήθηκε το αρχείο παράδοσης: " zip))
        (princ "\n** Το ZIP δεν δημιουργήθηκε - ελέγξτε τα ονόματα αρχείων. **"))))
  (princ))

;;; DGMSIGN - Άνοιγμα του PDF στο JSignPdf για ψηφιακή υπογραφή
(defun c:DGMSIGN ( / js pdf)
  (setq js (getenv "GFD_JSIGNPDF"))
  (if (or (null js) (null (findfile js)))
    (progn
      (princ "\nΕντοπίστε το εκτελέσιμο του JSignPdf (μία φορά - αποθηκεύεται).")
      (setq js (getfiled "Εντοπισμός JSignPdf.exe" "" "exe" 0))
      (if js (setenv "GFD_JSIGNPDF" js))))
  (if js
    (progn
      (setq pdf (getfiled "PDF προς υπογραφή" "" "pdf" 0))
      (if pdf
        (progn
          (startapp (strcat "\"" js "\"") (strcat "\"" pdf "\""))
          (princ "\nΆνοιξε το JSignPdf. Υπογράψτε το PDF και μετά εκτελέστε DGMZIP.")))))
  (princ))

;;; ============= ΜΑΖΙΚΗ ΠΑΡΑΓΩΓΗ ΠΙΝΑΚΩΝ ΣΥΝΤΕΤΑΓΜΕΝΩΝ =================

;; Κείμενα του layer PST_KAEK ως λίστα ((x y) . string)
(defun dgm:kaektexts ( / ss i d out)
  (setq out nil
        ss (ssget "_X" '((0 . "TEXT,MTEXT") (8 . "PST_KAEK"))))
  (if ss
    (progn
      (setq i 0)
      (while (< i (sslength ss))
        (setq d (entget (ssname ss i)))
        (setq out (cons (cons (list (cadr (assoc 10 d)) (caddr (assoc 10 d)))
                              (cdr (assoc 1 d)))
                        out))
        (setq i (1+ i)))))
  out)

;; Ο ΚΑΕΚ (ή οι ΚΑΕΚ, ενωμένοι με " / ") που βρίσκονται εντός του πολυγώνου
(defun dgm:kaekof (pts ktexts / out tx)
  (setq out nil)
  (foreach tx ktexts
    (if (dgm:inpoly (car tx) pts)
      (setq out (cons (cdr tx) out))))
  (cond
    ((null out) nil)
    ((= 1 (length out)) (car out))
    (t (apply 'strcat
              (cons (car out)
                    (mapcar '(lambda (s) (strcat " / " s)) (cdr out)))))))

;; Αφαίρεση προθέματος pre από το string s (αν υπάρχει)
(defun dgm:stripprefix (s pre)
  (if (and (>= (strlen s) (strlen pre)) (= (substr s 1 (strlen pre)) pre))
    (substr s (1+ (strlen pre)))
    s))

;;; DGMTA - Δημιουργία πινάκων συντεταγμένων των τμημάτων AREA_A
;;; (αποκοπτόμενα Αi) και AREA_D (διεκδικούμενα Δi). Τίτλος ανά τμήμα με
;;; το όνομά του (από AREA_x-labels) και τον ΚΑΕΚ του γεωτεμαχίου PST_KAEK
;;; μέσα στο οποίο βρίσκεται. Οι πίνακες στοιβάζονται αυτόματα.
;; Πυρήνας: πίνακες συντεταγμένων των τμημάτων Αi/Δi από τη θέση (x y)
;; προς τα κάτω. Επιστρέφει (πλήθος νέο-y).
(defun dgm:ta-core (h maxr x y / ktexts pstl pair kind lablay labs it e pts
                      ip nm kaek pp title ht cnt tx)
  (setq cnt 0)
  (dgm:marks-load)
  (setq ktexts (dgm:kaektexts)
        pstl (dgm:collect '("PST_KAEK") T))
  (dgm:layer-std "pinakas_sintetagmenon")
  (foreach pair (list (list "AREA_A" "ΑΠΟΚΟΠΤΟΜΕΝΟΥ" "AREA_A-labels")
                      (list "AREA_D" "ΔΙΕΚΔΙΚΟΥΜΕΝΟΥ" "AREA_D-labels"))
    (setq kind (cadr pair) lablay (caddr pair))
    (setq labs (dgm:laytexts lablay))
    (foreach it (dgm:collect (list (car pair)) T)
      (setq e (car it) pts (cadr it) ip (dgm:innerpt pts))
      ;; όνομα τμήματος από την ετικέτα (χωρίς το πρόθεμα "ΤΜΗΜΑ ")
      (setq nm nil)
      (foreach tx labs
        (if (and (null nm) (dgm:inpoly (car tx) pts))
          (setq nm (dgm:stripprefix (cdr tx) "ΤΜΗΜΑ "))))
      ;; ΚΑΕΚ του γεωτεμαχίου PST_KAEK που περιέχει το τμήμα
      (setq kaek nil)
      (foreach pp pstl
        (if (and (null kaek) ip (dgm:inpoly ip (cadr pp)))
          (setq kaek (dgm:kaekof (cadr pp) ktexts))))
      (setq title (strcat "ΠΙΝΑΚΑΣ ΣΥΝΤΕΤΑΓΜΕΝΩΝ ΚΟΡΥΦΩΝ " kind
                          " ΤΜΗΜΑΤΟΣ " (if nm nm "?")
                          " ΑΠΟ ΚΑΕΚ " (if kaek kaek "?")))
      (setq ht (dgm:coordtable e title h maxr x y))
      (setq y (- y ht (* 4.0 h)))
      (setq cnt (1+ cnt))))
  (list cnt y))

(defun c:DGMTA ( / h maxr ins r)
  (setq h (dgm:getreal "\nΎψος κειμένου πινάκων" dgm:*h*))
  (setq dgm:*h* h)
  (setq maxr (dgm:getint "\nΜέγιστες γραμμές ανά ομάδα στηλών" 30))
  (setq ins (getpoint "\nΣημείο εισαγωγής πινάκων (πάνω αριστερή γωνία): "))
  (if ins
    (progn
      (setq r (dgm:ta-core h maxr (car ins) (cadr ins)))
      (if (> (car r) 0)
        (princ (strcat "\nΔημιουργήθηκαν " (itoa (car r))
                       " πίνακες τμημάτων Αi/Δi."))
        (princ "\n** Δεν βρέθηκαν πολύγωνα στα layers AREA_A/AREA_D. **"))))
  (princ))

;;; DGMPALL - Αυτόματη παραγωγή πινάκων συντεταγμένων για όλες τις
;;; επιλεγμένες polylines. Τίτλος: layer + ΚΑΕΚ (από το κείμενο PST_KAEK
;;; εντός του πολυγώνου). Οι αριθμοί κορυφών διαβάζονται από τα σημάδια
;;; της DGMK. Οι πίνακες στοιβάζονται αυτόματα ο ένας κάτω από τον άλλον.
(defun c:DGMPALL ( / ss h maxr ins ktexts ord items pair rec e lay pts nums
                     n miss kaek title rows row len ng rowsper mrows heads
                     wids g idx y hh i p cnt)
  (princ "\nΕπιλέξτε polylines για παραγωγή πινάκων: ")
  (setq ss (ssget '((0 . "LWPOLYLINE"))))
  (if ss
    (progn
      (setq h (dgm:getreal "\nΎψος κειμένου πινάκων" dgm:*h*))
      (setq dgm:*h* h)
      (setq maxr (dgm:getint "\nΜέγιστες γραμμές ανά ομάδα στηλών" 30))
      (setq ins (getpoint "\nΣημείο εισαγωγής πινάκων (πάνω αριστερή γωνία): "))
      (if ins
        (progn
          (dgm:marks-load)
          (setq ktexts (dgm:kaektexts))
          (dgm:layer-std "pinakas_sintetagmenon")
          ;; σειρά πινάκων κατά προτεραιότητα layer (όπως το KtimaDGM)
          (setq ord '("PST_KAEK" "DGM_PROP_FINAL" "AREA_A" "AREA_D"
                      "TOPO_PROP" "TOPO_PROP_NEW" "BLD" "LINE_XM" "VST"
                      "VST_FINAL" "EAS" "EAS_FINAL" "LINE_XM_VST"))
          (setq items nil i 0)
          (while (< i (sslength ss))
            (setq e (ssname ss i))
            (setq lay (cdr (assoc 8 (entget e))))
            (setq items (cons (cons (- (length ord)
                                       (length (member lay ord)))
                                    (list e lay))
                              items))
            (setq i (1+ i)))
          (setq items (dgm:sortpairs (reverse items)))
          (setq y (cadr ins) cnt 0)
          (foreach pair items
            (setq rec (cdr pair)
                  e   (car rec)
                  lay (cadr rec))
            (setq pts (dgm:lwpts e))
            ;; αριθμοί κορυφών από τα σημάδια της DGMK
            (setq nums nil miss 0)
            (foreach p pts
              (setq n (dgm:findnum p dgm:*findtol*))
              (if (null n) (setq n "-" miss (1+ miss)))
              (setq nums (cons n nums)))
            (setq nums (reverse nums))
            (if (> miss 0)
              (princ (strcat "\n[ΠΡΟΣΟΧΗ] " lay ": " (itoa miss)
                             " κορυφές χωρίς αρίθμηση - εκτελέστε πρώτα DGMK.")))
            ;; ΚΑΕΚ εντός του πολυγώνου
            (setq kaek (if (dgm:closedp e) (dgm:kaekof pts ktexts)))
            (setq title (strcat "ΠΙΝΑΚΑΣ ΣΥΝΤΕΤΑΓΜΕΝΩΝ ΚΟΡΥΦΩΝ " lay
                                (cond
                                  (kaek (strcat " - ΚΑΕΚ " kaek))
                                  ((dgm:closedp e) " - ΑΓΝΩΣΤΟ ΚΑΕΚ")
                                  (t ""))))
            ;; γραμμές πίνακα
            (setq rows nil i 0)
            (while (< i (length pts))
              (setq p (nth i pts))
              (setq rows
                    (cons (list (nth i nums)
                                (rtos (car p) 2 3)
                                (rtos (cadr p) 2 3)
                                (if (> i 0)
                                  (strcat (nth (1- i) nums) " - " (nth i nums)
                                          ": "
                                          (rtos (distance (nth (1- i) pts) p) 2 2))
                                  ""))
                          rows))
              (setq i (1+ i)))
            (setq rows (reverse rows))
            (if (dgm:closedp e)
              (setq rows
                    (append rows
                            (list (list "" "" ""
                                        (strcat (last nums) " - " (car nums)
                                                ": "
                                                (rtos (distance (last pts) (car pts)) 2 2)))))))
            ;; σπάσιμο σε ομάδες στηλών
            (setq len (length rows)
                  ng (1+ (/ (1- len) maxr))
                  rowsper (1+ (/ (1- len) ng)))
            (setq mrows nil i 0)
            (while (< i rowsper)
              (setq row nil g 0)
              (while (< g ng)
                (setq idx (+ i (* g rowsper)))
                (setq row (append row
                                  (if (< idx len)
                                    (nth idx rows)
                                    (list "" "" "" ""))))
                (setq g (1+ g)))
              (setq mrows (cons row mrows))
              (setq i (1+ i)))
            (setq mrows (reverse mrows))
            (setq heads nil wids nil g 0)
            (while (< g ng)
              (setq heads (append heads
                                  (list (list "Σημείο") (list "Χ") (list "Y")
                                        (list "Αποστάσεις"))))
              (setq wids (append wids
                                 (list (* 8 h) (* 16 h) (* 16 h) (* 17 h))))
              (setq g (1+ g)))
            ;; σχεδίαση πίνακα
            (dgm:table (list (car ins) y) title heads wids mrows h
                       "pinakas_sintetagmenon"
                       (if (and (dgm:closedp e) (> (length pts) 2))
                         (strcat "Ε (" (dgm:perimstr nums T) ") = "
                                 (rtos (dgm:area pts) 2 2) " τ.μ.")
                         nil))
            (setq cnt (1+ cnt))
            ;; μετατόπιση για τον επόμενο πίνακα
            (setq hh (+ (* 2.4 h)
                        (* 2.7 h)
                        (* 2.0 h (length mrows))
                        (if (dgm:closedp e) (* 2.0 h) 0.0)
                        (* 4.0 h)))
            (setq y (- y hh)))
          (princ (strcat "\nΔημιουργήθηκαν " (itoa cnt) " πίνακες."))))))
  (princ))

;;; ========== ΠΛΗΡΩΣ ΑΥΤΟΜΑΤΗ ΑΡΙΘΜΗΣΗ + ΟΛΟΙ ΟΙ ΠΙΝΑΚΕΣ ==============

;; Κείμενα ενός layer ως λίστα ((x y) . string)
(defun dgm:laytexts (lay / ss i d out)
  (setq out nil
        ss (ssget "_X" (list '(0 . "TEXT,MTEXT") (cons 8 lay))))
  (if ss
    (progn
      (setq i 0)
      (while (< i (sslength ss))
        (setq d (entget (ssname ss i)))
        (setq out (cons (cons (list (cadr (assoc 10 d)) (caddr (assoc 10 d)))
                              (cdr (assoc 1 d)))
                        out))
        (setq i (1+ i)))))
  out)

;; Αυτόματη αρίθμηση κορυφών σε λίστα polylines (κανόνας DGMK: κοινές
;; κορυφές = ένας αριθμός, υπάρχοντα σημάδια διατηρούνται).
(defun dgm:autonumber (ents tol h / n done e lay mlay a pts closed np k pt
                         f dd cnt ss)
  (setq n (dgm:getint "\nΑριθμός πρώτης κορυφής" (1+ dgm:*num*)))
  (dgm:marks-load)
  ;; αποφυγή επικάλυψης: όλα τα επιλεγμένα polylines
  (setq ss (ssadd))
  (foreach e ents (ssadd e ss))
  (dgm:avoid-init ss)
  (setq done nil cnt 0)
  (foreach e ents
    (setq lay  (cdr (assoc 8 (entget e)))
          mlay (strcat "σημείο_" lay)
          a    (assoc mlay dgm:*layers*))
    (dgm:layer mlay (if a (cadr a) 3))
    (setq pts (dgm:lwpts e) closed (dgm:closedp e) np (length pts) k 0)
    (while (< k np)
      (setq pt (nth k pts))
      (setq f nil)
      (foreach dd done
        (if (dgm:samept dd pt tol) (setq f T)))
      (cond
        (f nil)
        ((dgm:findnum pt dgm:*findtol*)
         (setq done (cons pt done)))
        (t
         (dgm:point pt mlay)
         (dgm:circle pt dgm:*vcirc* mlay)
         (dgm:placelabel pt pts closed k h (itoa n) mlay)
         (setq done (cons pt done))
         (setq n (1+ n) cnt (1+ cnt))))
      (setq k (1+ k))))
  (if (> cnt 0) (setq dgm:*num* (1- n)))
  cnt)

;; Πίνακας συντεταγμένων μίας polyline στη θέση (x y).
;; Επιστρέφει το συνολικό ύψος που κατέλαβε ο πίνακας.
(defun dgm:coordtable (e title h maxr x y / pts nums miss n rows row len ng
                         rowsper mrows heads wids g idx i p)
  (setq pts (dgm:lwpts e))
  (setq nums nil miss 0)
  (foreach p pts
    (setq n (dgm:findnum p dgm:*findtol*))
    (if (null n) (setq n "-" miss (1+ miss)))
    (setq nums (cons n nums)))
  (setq nums (reverse nums))
  (if (> miss 0)
    (princ (strcat "\n[ΠΡΟΣΟΧΗ] " (itoa miss)
                   " κορυφές χωρίς αρίθμηση στον πίνακα: " title)))
  (setq rows nil i 0)
  (while (< i (length pts))
    (setq p (nth i pts))
    (setq rows
          (cons (list (nth i nums)
                      (rtos (car p) 2 3)
                      (rtos (cadr p) 2 3)
                      (if (> i 0)
                        (strcat (nth (1- i) nums) " - " (nth i nums) ": "
                                (rtos (distance (nth (1- i) pts) p) 2 2))
                        ""))
                rows))
    (setq i (1+ i)))
  (setq rows (reverse rows))
  (if (dgm:closedp e)
    (setq rows
          (append rows
                  (list (list "" "" ""
                              (strcat (last nums) " - " (car nums) ": "
                                      (rtos (distance (last pts) (car pts)) 2 2)))))))
  (setq len (length rows)
        ng (1+ (/ (1- len) maxr))
        rowsper (1+ (/ (1- len) ng)))
  (setq mrows nil i 0)
  (while (< i rowsper)
    (setq row nil g 0)
    (while (< g ng)
      (setq idx (+ i (* g rowsper)))
      (setq row (append row
                        (if (< idx len) (nth idx rows) (list "" "" "" ""))))
      (setq g (1+ g)))
    (setq mrows (cons row mrows))
    (setq i (1+ i)))
  (setq mrows (reverse mrows))
  (setq heads nil wids nil g 0)
  (while (< g ng)
    (setq heads (append heads
                        (list (list "Σημείο") (list "Χ") (list "Y")
                              (list "Αποστάσεις"))))
    (setq wids (append wids (list (* 8 h) (* 16 h) (* 16 h) (* 17 h))))
    (setq g (1+ g)))
  (dgm:table (list x y) title heads wids mrows h "pinakas_sintetagmenon"
             (if (and (dgm:closedp e) (> (length pts) 2))
               (strcat "Ε (" (dgm:perimstr nums T) ") = "
                       (rtos (dgm:area pts) 2 2) " τ.μ.")
               nil))
  (+ (dgm:titleh title (* ng 57.0 h) h) (* 2.7 h) (* 2.0 h (length mrows))
     (if (dgm:closedp e) (* 2.0 h) 0.0)))

;; Εμβαδόν επικάλυψης δύο πολυγώνων: (Ea + Eb - E(XOR)) / 2
(defun dgm:ovarea (a b tol / sx)
  (if (dgm:overlapp a b tol)
    (progn
      (setq sx 0.0)
      (foreach l (dgm:xorloops (list a b) tol) (setq sx (+ sx (dgm:area l))))
      (max 0.0 (/ (- (+ (dgm:area a) (dgm:area b)) sx) 2.0)))
    0.0))

;; Αντιστοίχιση αρχικών (PST_KAEK) με τελικά (DGM_PROP_FINAL) γεωτεμάχια.
;; Σε κάθε αρχικό αντιστοιχούν τα τελικά που βρίσκονται κατά το μεγαλύτερο
;; μέρος τους μέσα του (υπόλοιπα/τμήματα κατάτμησης)· αν δεν υπάρχει κανένα,
;; το τελικό που καλύπτει πάνω από το μισό αρχικό (π.χ. το δικό μας όριο).
;; Επιστρέφει (ζεύγη αταίριαστα): ζεύγη = ((pst-item (fin-item ...)) ...).
(defun dgm:pairfinals (pstl dgml tol / pairs used lst best bo o rest)
  (setq pairs nil used nil)
  (foreach it pstl
    (setq lst nil best nil bo 0.0)
    (foreach g dgml
      (setq o (dgm:ovarea (cadr it) (cadr g) tol))
      (if (> o (* 0.5 (dgm:area (cadr g)))) (setq lst (cons g lst)))
      (if (> o bo) (setq bo o best g)))
    (if (and (null lst) best (> bo (* 0.5 (dgm:area (cadr it)))))
      (setq lst (list best)))
    (setq lst (reverse lst))
    (foreach g lst (setq used (cons (car g) used)))
    (setq pairs (cons (list it lst) pairs)))
  (setq rest nil)
  (foreach g dgml
    (if (not (member (car g) used)) (setq rest (cons g rest))))
  (list (reverse pairs) (reverse rest)))

;; Τίτλος ΚΑΕΚ τελικού γεωτεμαχίου: το κείμενο μέσα του, αλλιώς (κανένα ή
;; περισσότερα κείμενα) ο ΚΑΕΚ του αντίστοιχου αρχικού.
(defun dgm:finkaek (g pk ktexts / kg)
  (setq kg (dgm:kaekof (cadr g) ktexts))
  (cond ((and kg (not (wcmatch kg "*/*"))) kg)
        (pk pk)
        (kg kg)
        (t "ΑΓΝΩΣΤΟ")))

;;; DGMAUTO - Αυτόματη αρίθμηση + όλοι οι πίνακες για όλα τα πολύγωνα
;;; των layers PST_KAEK (αρχικά ΚΑΕΚ) και DGM_PROP_FINAL (τελικά ΚΑΕΚ):
;;; πίνακες συντεταγμένων, πίνακας αρχικών-τελικών εμβαδών, και πίνακας
;;; για τη διόρθωση των γεωτεμαχίων (από τα AREA_A/AREA_D αν υπάρχουν).
(defun c:DGMAUTO ( / h tol maxr ins x y topol pstl dgml areal ents ktexts it pts
                     kaek title ht rows a1 a2 fmt tx heads wids labs pair lp
                     nm ip apo se cnt pp dp k pr pairs pr2 ng xr yr g)
  (setq topol (dgm:collect '("TOPO_PROP") T)
        pstl  (dgm:collect '("PST_KAEK") T)
        dgml  (dgm:collect '("DGM_PROP_FINAL") T)
        areal (dgm:collect '("AREA_A" "AREA_D") T))
  (if (and (null pstl) (null topol))
    (princ "\n** Δεν υπάρχουν κλειστά πολύγωνα στα layers PST_KAEK / TOPO_PROP. **")
    (progn
      (setq h (dgm:getreal "\nΎψος κειμένου" dgm:*h*))
      (setq dgm:*h* h)
      (setq tol (dgm:getreal "\nΑνοχή ταύτισης κορυφών (m)" 0.001))
      (setq maxr (dgm:getint "\nΜέγιστες γραμμές ανά ομάδα στηλών" 30))
      (setq ins (getpoint "\nΣημείο εισαγωγής πινάκων (πάνω αριστερή γωνία): "))
      (if ins
        (progn
          (setq x (car ins) y (cadr ins))
          ;; 1. Αυτόματη αρίθμηση κορυφών (ιδιοκτησία, αρχικά, τελικά, τμήματα
          ;;    Α/Δ) ΣΥΝΟΛΙΚΑ: κοινές κορυφές παίρνουν έναν αριθμό.
          (setq ents (append (mapcar 'car topol)
                             (mapcar 'car pstl)
                             (mapcar 'car dgml)
                             (mapcar 'car areal)))
          (setq cnt (dgm:autonumber ents tol h))
          (princ (strcat "\nΑριθμήθηκαν " (itoa cnt) " νέες κορυφές σε "
                         (itoa (length ents)) " πολύγωνα."))
          ;; 2. Πίνακες συντεταγμένων
          (dgm:marks-load)
          (setq ktexts (dgm:kaektexts))
          (dgm:layer-std "pinakas_sintetagmenon")
          ;; 2α. Πίνακες ιδιοκτησίας (TOPO_PROP)
          (setq k 1)
          (foreach it topol
            (setq title (strcat "ΓΕΩΤΕΜΑΧΙΟ \"" (itoa k) "\" - (TOPO_PROP)"))
            (setq ht (dgm:coordtable (car it) title h maxr x y))
            (setq y (- y ht (* 4.0 h)))
            (setq k (1+ k)))
          ;; 2β. ΔΥΟ ΣΤΗΛΕΣ: αριστερά ο πίνακας κάθε αρχικού ΚΑΕΚ (PST_KAEK),
          ;;     δεξιά ο πίνακας του αντίστοιχου ΚΑΕΚ μετά τη μεταβολή
          (princ "\nΑντιστοίχιση αρχικών - τελικών γεωτεμαχίων...")
          (setq pr (dgm:pairfinals pstl dgml tol)
                pairs (car pr))
          (setq ng 1)
          (foreach it (append topol pstl)
            (setq ng (max ng (1+ (/ (length (cadr it)) maxr)))))
          (setq xr (+ x (* ng 57.0 h) (* 6.0 h)))
          (foreach pr2 pairs
            (setq it (car pr2)
                  kaek (dgm:kaekof (cadr it) ktexts))
            (setq title (strcat "ΠΙΝΑΚΑΣ ΣΥΝΤΕΤΑΓΜΕΝΩΝ ΚΟΡΥΦΩΝ ΑΡΧΙΚΟΥ ΓΕΩΤΕΜΑΧΙΟΥ ΜΕ ΚΑΕΚ "
                                (if kaek kaek "ΑΓΝΩΣΤΟ")))
            (setq ht (dgm:coordtable (car it) title h maxr x y))
            (setq yr y)
            (foreach g (cadr pr2)
              (setq title (strcat "ΠΙΝΑΚΑΣ ΣΥΝΤΕΤΑΓΜΕΝΩΝ ΚΟΡΥΦΩΝ ΤΕΛΙΚΟΥ ΓΕΩΤΕΜΑΧΙΟΥ ΜΕ ΚΑΕΚ "
                                  (dgm:finkaek g kaek ktexts)
                                  " ΓΙΑ ΤΗΝ ΕΝΗΜΕΡΩΣΗ ΤΗΣ ΚΤΗΜΑΤΟΛΟΓΙΚΗΣ ΒΑΣΗΣ"))
              (setq yr (- yr (dgm:coordtable (car g) title h maxr xr yr)
                          (* 4.0 h))))
            (setq y (min (- y ht (* 4.0 h)) yr)))
          ;; τελικά χωρίς αντίστοιχο αρχικό (δεξιά στήλη)
          (setq yr y)
          (foreach g (cadr pr)
            (setq title (strcat "ΠΙΝΑΚΑΣ ΣΥΝΤΕΤΑΓΜΕΝΩΝ ΚΟΡΥΦΩΝ ΤΕΛΙΚΟΥ ΓΕΩΤΕΜΑΧΙΟΥ ΜΕ ΚΑΕΚ "
                                (dgm:finkaek g nil ktexts)
                                " ΓΙΑ ΤΗΝ ΕΝΗΜΕΡΩΣΗ ΤΗΣ ΚΤΗΜΑΤΟΛΟΓΙΚΗΣ ΒΑΣΗΣ"))
            (setq yr (- yr (dgm:coordtable (car g) title h maxr xr yr)
                        (* 4.0 h))))
          (setq y (min y yr))
          ;; 3. Πίνακας αρχικών και τελικών εμβαδών (ανά αρχικό ΚΑΕΚ με τελικό
          ;;    όριο, και ανά κείμενο ΝΕΟ)
          (setq rows nil)
          (foreach pr2 pairs
            (if (cadr pr2)
              (progn
                (setq kaek (dgm:kaekof (cadr (car pr2)) ktexts) a2 0.0)
                (foreach g (cadr pr2) (setq a2 (+ a2 (dgm:area (cadr g)))))
                (setq rows (cons (list (if kaek kaek "ΑΓΝΩΣΤΟ")
                                       (rtos (dgm:area (cadr (car pr2))) 2 2)
                                       (rtos a2 2 2))
                                 rows)))))
          (foreach tx ktexts
            (if (eq 'NEO (dgm:kaekfmt (cdr tx)))
              (progn
                (setq a2 nil)
                (foreach dp dgml
                  (if (dgm:inpoly (car tx) (cadr dp))
                    (setq a2 (+ (if a2 a2 0.0) (dgm:area (cadr dp))))))
                (setq rows (cons (list (cdr tx) "-"
                                       (if a2 (rtos a2 2 2) "-"))
                                 rows)))))
          (setq rows (reverse rows))
          (if rows
            (progn
              (setq heads (list (list "ΕΜΠΛΕΚΟΜΕΝΑ ΚΑΕΚ")
                                (list "ΑΡΧΙΚΟ ΕΜΒΑΔΟΝ" "(τ.μ.)")
                                (list "ΤΕΛΙΚΟ ΕΜΒΑΔΟΝ ΜΕΤΑ ΤΗ"
                                      "ΔΙΟΡΘΩΣΗ ΤΩΝ ΟΡΙΩΝ ΒΑΣΕΙ"
                                      "ΑΙΤΗΣΗΣ / ΔΙΚΟΓΡΑΦΟΥ (τ.μ.)"))
                    wids (list (* 22 h) (* 16 h) (* 26 h)))
              (dgm:table (list x y)
                         "ΠΙΝΑΚΑΣ ΑΡΧΙΚΩΝ ΚΑΙ ΤΕΛΙΚΩΝ ΕΜΒΑΔΩΝ ΕΠΗΡΕΑΖΟΜΕΝΩΝ ΓΕΩΤΕΜΑΧΙΩΝ"
                         heads wids rows h "pinakas_sintetagmenon" nil)
              (setq y (- y (* 2.4 h) (* 5.7 h) (* 2.0 h (length rows))
                         (* 4.0 h)))))
          ;; 4. Πίνακας για τη διόρθωση των γεωτεμαχίων (από AREA_A/AREA_D)
          (setq rows nil)
          (foreach pair '(("AREA_A" . "AREA_A-labels")
                          ("AREA_D" . "AREA_D-labels"))
            (setq labs (dgm:laytexts (cdr pair)))
            (foreach lp (dgm:collect (list (car pair)) T)
              (setq pts (cadr lp)
                    ip (dgm:innerpt pts)
                    nm nil apo nil se nil)
              (foreach tx labs
                (if (and (null nm) (dgm:inpoly (car tx) pts))
                  (setq nm (cdr tx))))
              (foreach pp pstl
                (if (and (null apo) ip (dgm:inpoly ip (cadr pp)))
                  (setq apo (dgm:kaekof (cadr pp) ktexts))))
              ;; ΣΕ ΚΑΕΚ: ο ΚΑΕΚ του αρχικού που αντιστοιχεί στο τελικό
              ;; γεωτεμάχιο το οποίο περιέχει το τμήμα
              (foreach dp dgml
                (if (and (null se) ip (dgm:inpoly ip (cadr dp)))
                  (progn
                    (foreach pr2 pairs
                      (if (and (null se) (member dp (cadr pr2)))
                        (setq se (dgm:kaekof (cadr (car pr2)) ktexts))))
                    (if (null se) (setq se (dgm:kaekof (cadr dp) ktexts))))))
              (setq rows (cons (list (if nm nm "-")
                                     (rtos (dgm:area pts) 2 2)
                                     (if apo apo "-")
                                     (if se se "-"))
                               rows))))
          (setq rows (reverse rows))
          (if rows
            (progn
              (setq heads (list (list "ΤΜΗΜΑ")
                                (list "ΕΜΒΑΔΟΝ" "(τ.μ.)")
                                (list "ΑΠΟ ΚΑΕΚ")
                                (list "ΣΕ ΚΑΕΚ"))
                    wids (list (* 10 h) (* 14 h) (* 18 h) (* 18 h)))
              (dgm:table (list x y)
                         "ΠΙΝΑΚΑΣ ΓΙΑ ΤΗ ΔΙΟΡΘΩΣΗ ΤΩΝ ΓΕΩΤΕΜΑΧΙΩΝ"
                         heads wids rows h "pinakas_sintetagmenon" nil)
              (setq y (- y (* 2.4 h) (* 5.7 h) (* 2.0 h (length rows))
                         (* 4.0 h)))
              ;; 5. Πίνακες συντεταγμένων των τμημάτων Αi / Δi
              (setq pp (dgm:ta-core h maxr x y))
              (princ (strcat "\nΠίνακες τμημάτων Αi/Δi: " (itoa (car pp)) ".")))
            (princ "\n[INFO] Δεν υπάρχουν πολύγωνα AREA_A/AREA_D - οι πίνακες διόρθωσης και τμημάτων παραλείφθηκαν."))
          (princ (strcat "\nΟλοκληρώθηκε: πίνακες για "
                         (itoa (length topol)) " ιδιοκτησίες (TOPO_PROP), "
                         (itoa (length pstl)) " αρχικά και "
                         (itoa (length dgml)) " τελικά γεωτεμάχια."))))))
  (princ))

;;; ================= ΚΛΙΜΑΚΑ - ΚΑΝΑΒΟΣ - ΒΟΡΡΑΣ =========================

;; Ερώτηση κλίμακας σχεδίασης - επιστρέφει και αποθηκεύει τον παρονομαστή
(defun dgm:askscale ( / k def)
  (setq def (cond ((null dgm:*scale*) 3)
                  ((= dgm:*scale* 100) 1)
                  ((= dgm:*scale* 200) 2)
                  ((= dgm:*scale* 1000) 4)
                  ((= dgm:*scale* 2000) 5)
                  (t 3)))
  (princ "\nΚλίμακα σχεδίασης:")
  (princ "\n  1 = 1:100   2 = 1:200   3 = 1:500   4 = 1:1000   5 = 1:2000")
  (setq k (dgm:getint "\nΕπιλογή" def))
  (setq dgm:*scale*
        (cond ((= k 1) 100) ((= k 2) 200) ((= k 4) 1000)
              ((= k 5) 2000) (t 500)))
  ;; προτεινόμενο ύψος κειμένων = 2 mm στην εκτύπωση
  (setq dgm:*h* (* 0.002 dgm:*scale*))
  dgm:*scale*)

;;; DGMSCALE - Ορισμός κλίμακας σχεδίασης
(defun c:DGMSCALE ( / m)
  (setq m (dgm:askscale))
  (setvar "LTSCALE" (/ m 100.0))
  (princ (strcat "\nΟρίστηκε κλίμακα σχεδίασης 1:" (itoa m)
                 ". Προτεινόμενο ύψος κειμένων: "
                 (rtos dgm:*h* 2 2) " m (2 mm εκτύπωσης), LTSCALE = "
                 (rtos (/ m 100.0) 2 2) "."))
  (princ))

;; Σύμβολο βορρά στο σημείο pt (κατακόρυφο, προς τα πάνω), μέγεθος ανά κλίμακα
(defun dgm:north (pt m / x y r)
  (setq x (car pt) y (cadr pt)
        r (* 0.01 m))                       ; ακτίνα κύκλου = 10 mm εκτύπωσης
  (dgm:layer "KANABOS" 8)
  ;; κύκλος
  (dgm:circle (list x y) r "KANABOS")
  ;; βελόνα (κλειστό περίγραμμα): κορυφή - δεξιά βάση - κέντρο - αριστερή βάση
  (dgm:mkpoly (list (list x (+ y (* 1.30 r)))
                    (list (+ x (* 0.30 r)) (- y (* 0.80 r)))
                    (list x (- y (* 0.40 r)))
                    (list (- x (* 0.30 r)) (- y (* 0.80 r))))
              "KANABOS" T)
  ;; γεμισμένο αριστερό μισό της βελόνας
  (entmake (list '(0 . "SOLID") '(8 . "KANABOS")
                 (cons 10 (list x (+ y (* 1.30 r)) 0.0))
                 (cons 11 (list (- x (* 0.30 r)) (- y (* 0.80 r)) 0.0))
                 (cons 12 (list x (- y (* 0.40 r)) 0.0))
                 (cons 13 (list x (- y (* 0.40 r)) 0.0))))
  ;; γράμμα Β πάνω από την κορυφή
  (dgm:textc (list x (+ y (* 1.75 r))) (* 0.65 r) "Β" "KANABOS")
  (princ))

;;; DGMGRID - Κάναβος σχεδίασης + σύμβολο βορρά
(defun c:DGMGRID ( / m step p1 p2 xmin ymin xmax ymax x0 y0 xlast ylast
                    x y arm h lbl dec pt s)
  ;; α) κλίμακα, αν δεν έχει οριστεί
  (if (null dgm:*scale*)
    (progn
      (princ "\nΔεν έχει οριστεί κλίμακα σχεδίασης.")
      (dgm:askscale)))
  (setq m dgm:*scale*)
  ;; β) βήμα κανάβου
  (setq step (dgm:getreal "\nΒήμα κανάβου (m)" (/ m 10.0)))
  (if (<= step 0.0) (setq step (/ m 10.0)))
  (setq p1 (getpoint "\nΠρώτη γωνία περιοχής κανάβου: "))
  (setq p2 (if p1 (getcorner p1 "\nΑπέναντι γωνία: ")))
  (if (and p1 p2)
    (progn
      (setq xmin (min (car p1) (car p2))  xmax (max (car p1) (car p2))
            ymin (min (cadr p1) (cadr p2)) ymax (max (cadr p1) (cadr p2)))
      ;; ευθυγράμμιση σε ακέραια πολλαπλάσια του βήματος (ΕΓΣΑ '87)
      (setq x0 (* step (fix (/ xmin step))))
      (while (< x0 xmin) (setq x0 (+ x0 step)))
      (setq y0 (* step (fix (/ ymin step))))
      (while (< y0 ymin) (setq y0 (+ y0 step)))
      ;; τελευταία γραμμή/στήλη εντός της περιοχής
      (setq xlast (+ x0 (* step (fix (+ 1e-9 (/ (- xmax x0) step)))))
            ylast (+ y0 (* step (fix (+ 1e-9 (/ (- ymax y0) step))))))
      (dgm:layer "KANABOS" 8)
      (setq arm (* 0.0025 m)               ; μισό σκέλος σταυρού = 2.5 mm
            h   (* 0.002 m)                ; ύψος κειμένων = 2 mm
            dec (if (equal step (float (fix step)) 1e-9) 0 2))
      (setq lbl (dgm:getint "\nΑναγραφή συντεταγμένων περιμετρικά; 1 = Ναι, 0 = Όχι" 1))
      ;; πλαίσιο κανάβου ως κλειστή polyline
      (dgm:mkpoly (list (list x0 y0) (list xlast y0)
                        (list xlast ylast) (list x0 ylast))
                  "KANABOS" T)
      (setq x x0)
      (while (<= x (+ xmax 1e-9))
        (setq y y0)
        (while (<= y (+ ymax 1e-9))
          ;; σταυρός κανάβου
          (dgm:line (list (- x arm) y) (list (+ x arm) y) "KANABOS")
          (dgm:line (list x (- y arm)) (list x (+ y arm)) "KANABOS")
          (if (= lbl 1)
            (progn
              ;; τιμές Χ κάτω από την πρώτη σειρά, κατακόρυφα (rotation 90°)
              (if (equal y y0 1e-9)
                (progn
                  (setq s (rtos x 2 dec))
                  (dgm:textcr (list x (- y0 (* h (+ 1.5 (* 0.45 (strlen s))))))
                              h s "KANABOS" (* 0.5 pi))))
              ;; τιμές Υ αριστερά της πρώτης στήλης (οριζόντια)
              (if (equal x x0 1e-9)
                (dgm:textc (list (- x0 (* 4.5 h)) y) h (rtos y 2 dec) "KANABOS"))))
          (setq y (+ y step)))
        (setq x (+ x step)))
      (princ (strcat "\nΣχεδιάστηκε κάναβος με βήμα " (rtos step 2 dec)
                     " m (κλίμακα 1:" (itoa m) ") + πλαίσιο, στο layer KANABOS."))
      ;; σύμβολο βορρά
      (setq pt (getpoint "\nΘέση συμβόλου βορρά (Enter για παράλειψη): "))
      (if pt (dgm:north pt m))))
  (princ))

;; Όρια (xmin ymin xmax ymax) όλων των LWPOLYLINE/LINE του σχεδίου
(defun dgm:bbox ( / ss i e d et pts xmin ymin xmax ymax)
  (setq ss (ssget "_X" '((0 . "LWPOLYLINE,LINE"))))
  (if ss
    (progn
      (setq i 0)
      (while (< i (sslength ss))
        (setq e (ssname ss i) d (entget e) et (cdr (assoc 0 d)) pts nil)
        (cond
          ((= et "LINE")
           (setq pts (list (cdr (assoc 10 d)) (cdr (assoc 11 d)))))
          ((= et "LWPOLYLINE")
           (setq pts (dgm:lwpts e))))
        (foreach p pts
          (if (null xmin)
            (setq xmin (car p) xmax (car p) ymin (cadr p) ymax (cadr p))
            (progn
              (if (< (car p) xmin) (setq xmin (car p)))
              (if (> (car p) xmax) (setq xmax (car p)))
              (if (< (cadr p) ymin) (setq ymin (cadr p)))
              (if (> (cadr p) ymax) (setq ymax (cadr p))))))
        (setq i (1+ i)))))
  (if xmin (list xmin ymin xmax ymax)))

;;; DGMSHEET - Κάναβος-φύλλο: ύψος = 609 mm x κλίμακα (σταθερό, χαρτί),
;;; μήκος τέτοιο ώστε να περιλαμβάνει όλες τις polylines/lines του σχεδίου.
(defun c:DGMSHEET ( / m step bb xmin ymin xmax ymax gh yc yb ytop xl xr
                     arm h dec lbl x y s)
  (if (null dgm:*scale*)
    (progn (princ "\nΔεν έχει οριστεί κλίμακα σχεδίασης.") (dgm:askscale)))
  (setq m dgm:*scale*)
  (setq step (dgm:getreal "\nΒήμα κανάβου (m)" (/ m 10.0)))
  (if (<= step 0.0) (setq step (/ m 10.0)))
  (setq bb (dgm:bbox))
  (if (null bb)
    (princ "\n** Δεν βρέθηκαν polylines/lines στο σχέδιο. **")
    (progn
      (setq xmin (car bb) ymin (cadr bb) xmax (caddr bb) ymax (cadddr bb))
      (setq gh (* 0.609 m))              ; ύψος χαρτιού 609 mm σε μονάδες εδάφους
      ;; κατακόρυφα: κεντράρισμα περιεχομένου, κάτω ακμή σε ακέραιο βήμα
      (setq yc (/ (+ ymin ymax) 2.0)
            yb (* step (fix (/ (- yc (/ gh 2.0)) step)))
            ytop (+ yb gh))
      ;; οριζόντια: αριστερή ακμή <= xmin, δεξιά ακμή >= xmax, σε βήματα
      (setq xl (* step (fix (/ xmin step))))
      (while (> xl xmin) (setq xl (- xl step)))
      (setq xr xl)
      (while (< xr xmax) (setq xr (+ xr step)))
      (dgm:layer "KANABOS" 8)
      (setq arm (* 0.0025 m) h (* 0.002 m)
            dec (if (equal step (float (fix step)) 1e-9) 0 2))
      (if (> (- ymax ymin) gh)
        (princ (strcat "\n[ΠΡΟΣΟΧΗ] Το περιεχόμενο (ύψος "
                       (rtos (- ymax ymin) 2 1) " m) ξεπερνά το ύψος του φύλλου ("
                       (rtos gh 2 1) " m) στην κλίμακα 1:" (itoa m)
                       " - χρειάζεται μικρότερη κλίμακα.")))
      (setq lbl (dgm:getint "\nΑναγραφή συντεταγμένων περιμετρικά; 1 = Ναι, 0 = Όχι" 1))
      ;; πλαίσιο φύλλου (κλειστή polyline)
      (dgm:mkpoly (list (list xl yb) (list xr yb) (list xr ytop) (list xl ytop))
                  "KANABOS" T)
      ;; σταυροί κανάβου + ετικέτες σε ακέραιες συντεταγμένες εντός του φύλλου
      (setq x xl)
      (while (<= x (+ xr 1e-9))
        (setq y yb)                       ; yb είναι ήδη ακέραιο βήμα
        (while (<= y (+ ytop 1e-9))
          (dgm:line (list (- x arm) y) (list (+ x arm) y) "KANABOS")
          (dgm:line (list x (- y arm)) (list x (+ y arm)) "KANABOS")
          (if (= lbl 1)
            (progn
              (if (equal y yb 1e-9)
                (progn
                  (setq s (rtos x 2 dec))
                  (dgm:textcr (list x (- yb (* h (+ 1.5 (* 0.45 (strlen s))))))
                              h s "KANABOS" (* 0.5 pi))))
              (if (equal x xl 1e-9)
                (dgm:textc (list (- xl (* 4.5 h)) y) h (rtos y 2 dec) "KANABOS"))))
          (setq y (+ y step)))
        (setq x (+ x step)))
      (princ (strcat "\nΦύλλο κανάβου: ύψος " (rtos gh 2 1)
                     " m (609 mm x 1:" (itoa m) "), μήκος "
                     (rtos (- xr xl) 2 1) " m, βήμα " (rtos step 2 dec)
                     " m, στο layer KANABOS."))))
  (princ))

;;; ================ ΣΚΑΡΙΦΗΜΑΤΑ ΑΡΧΙΚΩΝ / ΤΕΛΙΚΩΝ ΚΑΕΚ ==================

;; Κεντροειδές πολυγώνου (nil αν εκφυλισμένο)
(defun dgm:centroid (pts / n i p1 p2 a cx cy cr)
  (setq n (length pts) i 0 a 0.0 cx 0.0 cy 0.0)
  (while (< i n)
    (setq p1 (nth i pts) p2 (nth (rem (1+ i) n) pts))
    (setq cr (- (* (car p1) (cadr p2)) (* (car p2) (cadr p1))))
    (setq a  (+ a cr)
          cx (+ cx (* (+ (car p1) (car p2)) cr))
          cy (+ cy (* (+ (cadr p1) (cadr p2)) cr)))
    (setq i (1+ i)))
  (if (> (abs a) 1e-9)
    (list (/ cx (* 3.0 a)) (/ cy (* 3.0 a)))))

;; Κέντρο πολυγώνου: κεντροειδές αν είναι εντός, αλλιώς εσωτερικό σημείο
(defun dgm:centerpt (pts / c)
  (setq c (dgm:centroid pts))
  (if (and c (dgm:inpoly c pts)) c (dgm:innerpt pts)))

;; Ορθογώνιο "παράθυρο" γύρω από κείμενο str ύψους h με κέντρο c
(defun dgm:textbox (c str h / hw hh)
  (setq hw (+ (* 0.35 h (strlen str)) (* 0.5 h))
        hh (+ (* 0.5 h) (* 0.5 h)))
  (list (list (- (car c) hw) (- (cadr c) hh))
        (list (+ (car c) hw) (- (cadr c) hh))
        (list (+ (car c) hw) (+ (cadr c) hh))
        (list (- (car c) hw) (+ (cadr c) hh))))

;; Ένας βρόχος ορίου HATCH (πολυγωνική διαδρομή)
(defun dgm:hatchloop (pts flag / lst)
  (setq lst (list (cons 92 flag) '(72 . 0) '(73 . 1) (cons 93 (length pts))))
  (foreach p pts
    (setq lst (cons (cons 10 (list (car p) (cadr p))) lst)))
  (reverse (cons '(97 . 0) (reverse lst))))

;; Solid HATCH με εξωτερικό όριο outer και προαιρετική εσωτερική "τρύπα"
;; inner (νησίδα), ώστε το κείμενο να μην καλύπτεται.
(defun dgm:solidhatch (outer inner lay col / d)
  (setq d (list '(0 . "HATCH") '(100 . "AcDbEntity") (cons 8 lay)
                (cons 62 col) '(100 . "AcDbHatch")
                '(10 0.0 0.0 0.0) '(210 0.0 0.0 1.0)
                '(2 . "SOLID") '(70 . 1) '(71 . 0)
                (cons 91 (if inner 2 1))))
  (setq d (append d (dgm:hatchloop outer 3)))
  (if inner (setq d (append d (dgm:hatchloop inner 2))))
  (setq d (append d (list '(75 . 1) '(76 . 1) '(98 . 0))))
  (entmake d))

;; Κεντραρισμένο κείμενο με ρητό χρώμα (για ευανάγνωστη ετικέτα σε solid)
(defun dgm:textcC (pt h str lay col)
  (entmake (list '(0 . "TEXT") (cons 8 lay) (cons 62 col)
                 (cons 10 (list (car pt) (cadr pt) 0.0))
                 (cons 11 (list (car pt) (cadr pt) 0.0))
                 (cons 40 h) (cons 1 str) '(50 . 0.0)
                 '(72 . 1) '(73 . 2))))

;;; DGMSKETCH - Σκαρίφημα Αρχικών (PST_KAEK, καφέ) ή Τελικών
;;; (DGM_PROP_FINAL, μπλε) ΚΑΕΚ σε σημείο που επιλέγει ο χρήστης:
;;; αντίγραφα των πολυγώνων + solid hatch + ετικέτα ΚΑΕΚ στο κέντρο,
;;; μη καλυπτόμενη από το hatch (τρύπα-παράθυρο όπου χωράει).
(defun c:DGMSKETCH ( / typ src lay hlay col ktexts items allx ally minx miny
                       span inpt dx dy h it cpts p c s box island cnt)
  (princ "\nΣκαρίφημα:  1 = Αρχικών ΚΑΕΚ (PST_KAEK, καφέ)   2 = Τελικών ΚΑΕΚ (DGM_PROP_FINAL, μπλε)")
  (setq typ (dgm:getint "\nΕπιλογή" 1))
  (if (= typ 2)
    (setq src "DGM_PROP_FINAL" lay "SKARIF_TELIKA" col 5)
    (setq src "PST_KAEK" lay "SKARIF_ARXIKA" col 34))
  (setq items (dgm:collect (list src) T))
  (if (null items)
    (princ (strcat "\n** Δεν υπάρχουν κλειστά πολύγωνα στο layer " src ". **"))
    (progn
      (setq hlay (strcat lay "-hatch"))
      (dgm:layer lay col)
      (dgm:layer hlay col)
      (setq ktexts (dgm:kaektexts))
      ;; κάτω-αριστερή γωνία του συνόλου
      (setq allx nil ally nil)
      (foreach it items
        (foreach p (cadr it)
          (setq allx (cons (car p) allx) ally (cons (cadr p) ally))))
      (setq minx (apply 'min allx) miny (apply 'min ally)
            span (max (- (apply 'max allx) minx) (- (apply 'max ally) miny)))
      (setq inpt (getpoint "\nΣημείο τοποθέτησης σκαριφήματος (κάτω-αριστερά): "))
      (if inpt
        (progn
          (setq dx (- (car inpt) minx) dy (- (cadr inpt) miny))
          (setq h (dgm:getreal "\nΎψος κειμένου ΚΑΕΚ σκαριφήματος"
                               (if (> dgm:*h* 0) dgm:*h* (/ span 40.0))))
          (setq dgm:*h* h)
          (setq cnt 0)
          (foreach it items
            (setq cpts (mapcar '(lambda (p) (list (+ (car p) dx) (+ (cadr p) dy)))
                               (cadr it)))
            ;; κείμενο: πραγματικός ΚΑΕΚ (αρχικά) ή επεξεργάσιμο placeholder (τελικά)
            (setq s (if (= typ 2) "ΑΡΙΘΜΟΣ ΚΑΕΚ" (dgm:kaekof (cadr it) ktexts)))
            (setq c (dgm:centerpt cpts))
            ;; παράθυρο-τρύπα μόνο αν χωράει ολόκληρο εντός του πολυγώνου
            (setq island nil)
            (if (and s c)
              (progn
                (setq box (dgm:textbox c s h))
                (if (and (dgm:inpoly (car box) cpts)
                         (dgm:inpoly (cadr box) cpts)
                         (dgm:inpoly (caddr box) cpts)
                         (dgm:inpoly (cadddr box) cpts))
                  (setq island box))))
            ;; solid hatch (κάτω), περίγραμμα, κείμενο (πάνω, ACI 7)
            (dgm:solidhatch cpts island hlay col)
            (dgm:mkpoly cpts lay T)
            (if (and s c) (dgm:textcC c h s lay 7))
            (setq cnt (1+ cnt)))
          (princ (strcat "\nΔημιουργήθηκε σκαρίφημα "
                         (if (= typ 2) "Τελικών" "Αρχικών")
                         " ΚΑΕΚ με " (itoa cnt) " γεωτεμάχια (layers "
                         lay " / " hlay ")."))))))
  (princ))

;;; DGMNEAR - Εντοπισμός "σχεδόν-συμπιπτουσών" κορυφών στα layers του ΔΓΜ.
;;; Εξετάζει ΜΟΝΟ τις polylines των layers που αφορούν το ΔΓΜ και επισημαίνει
;;; κάθε κορυφή που ΔΕΝ ταυτίζεται με άλλη (ίδιας ή άλλης polyline) αλλά
;;; απέχει σε ζώνη [dgm:*nearlo*, dgm:*nearhi*] (προεπιλογή 0.0004-0.005 m).
;;; Τις κυκλώνει με εμφανή κόκκινο κύκλο και αναφέρει το πλήθος τους.
(if (null dgm:*nearlo*) (setq dgm:*nearlo* 0.0004))
(if (null dgm:*nearhi*) (setq dgm:*nearhi* 0.005))

;; Layers ΔΓΜ των οποίων οι κορυφές πρέπει να ταυτίζονται
(setq dgm:*near-layers*
 '("PST_KAEK" "DGM_PROP_FINAL" "TOPO_PROP" "TOPO_PROP_NEW"
   "AREA_A" "AREA_D" "LINE_XM" "LINE_XM_VST"
   "VST_FINAL" "EAS_FINAL" "MINE_FINAL"
   "BOUND_IMPL" "BOUND_UNIMPL"))

(defun c:DGMNEAR ( / ss i pts p allv sorted l m a b idx j flags fp prev
                     uniq r cnt lo hi flt)
  (setq lo (dgm:getreal "\nΚάτω όριο ζώνης απόστασης (m)" dgm:*nearlo*))
  (setq hi (dgm:getreal "\nΑνω όριο ζώνης απόστασης (m)" dgm:*nearhi*))
  (setq dgm:*nearlo* lo dgm:*nearhi* hi)
  ;; καθάρισμα προηγούμενων σημαδιών
  (setq ss (ssget "_X" '((8 . "KONTINES"))))
  (if ss (progn (setq i 0)
                (while (< i (sslength ss)) (entdel (ssname ss i))
                       (setq i (1+ i)))))
  ;; φίλτρο layers (λίστα χωρισμένη με κόμμα)
  (setq flt (car dgm:*near-layers*))
  (foreach p (cdr dgm:*near-layers*) (setq flt (strcat flt "," p)))
  ;; συλλογή κορυφών ΜΟΝΟ από polylines των ΔΓΜ layers
  (setq allv nil)
  (setq ss (ssget "_X" (list '(0 . "LWPOLYLINE") (cons 8 flt))))
  (if (null ss)
    (princ "\n** Δεν βρέθηκαν polylines στα layers του ΔΓΜ. **")
    (progn
      (setq i 0)
      (while (< i (sslength ss))
        (setq pts (dgm:lwpts (ssname ss i)))
        (foreach p pts (setq allv (cons (cons (car p) p) allv)))
        (setq i (1+ i)))
      ;; ταξινόμηση κατά x για σάρωση με παράθυρο πλάτους hi
      (setq sorted (mapcar 'cdr (dgm:sortpairs allv)))
      (setq flags nil idx 0 l sorted)
      (while l
        (setq a (car l) m (cdr l) j (1+ idx))
        (while (and m (< (- (car (car m)) (car a)) hi))
          (setq b (car m))
          ;; μέσα στη ζώνη: δεν ταυτίζεται (>= lo) αλλά κοντά (<= hi)
          (if (and (>= (distance a b) lo) (<= (distance a b) hi))
            (setq flags (cons (cons idx a) (cons (cons j b) flags))))
          (setq m (cdr m) j (1+ j)))
        (setq l (cdr l) idx (1+ idx)))
      ;; μοναδικές κορυφές (κατά δείκτη)
      (setq flags (dgm:sortpairs flags) prev -1 uniq nil)
      (foreach fp flags
        (if (/= (car fp) prev)
          (setq uniq (cons (cdr fp) uniq) prev (car fp))))
      (setq cnt (length uniq))
      (if (= cnt 0)
        (princ (strcat "\nΔεν βρέθηκαν σχεδόν-συμπίπτουσες κορυφές στη ζώνη "
                       (rtos lo 2 4) " - " (rtos hi 2 4) " m."))
        (progn
          (dgm:layer-lw "KONTINES" 1 40)
          (setq r (if dgm:*scale* (* 0.004 dgm:*scale*) 0.5))
          (foreach p uniq (dgm:circle p r "KONTINES"))
          (princ (strcat "\nΒρέθηκαν " (itoa cnt)
                         " σχεδόν-συμπίπτουσες κορυφές (ζώνη " (rtos lo 2 4)
                         " - " (rtos hi 2 4)
                         " m) - επισημάνθηκαν με κόκκινους κύκλους (layer KONTINES).")))))
    )
  (princ))

;;; ============== ΑΠΟΣΠΑΣΜΑ ΟΡΘΟΦΩΤΟΧΑΡΤΗ (Κτηματολόγιο WMS) ============
;;; DGMORTHO - κατεβάζει ορθοφωτογραφία του bbox της TOPO_PROP από την
;;; υπηρεσία WMS του Ελληνικού Κτηματολογίου και την εισάγει γεωαναφερμένη
;;; στο σχέδιο.
;;;
;;; ΣΗΜΑΝΤΙΚΟ: Η υπηρεσία BASEMAP σερβίρει εικόνα ΜΟΝΟ σε EPSG:4326 (WGS84
;;; γεωγραφικές μοίρες lon/lat). Σε EPSG:2100 (ΕΓΣΑ87) επιστρέφει λευκή/κενή
;;; εικόνα. Γι' αυτό το σχέδιο είναι σε ΕΓΣΑ87 αλλά το αίτημα GetMap γίνεται
;;; σε EPSG:4326: μετατρέπουμε το bbox ΕΓΣΑ87 -> WGS84, ζητάμε την εικόνα, και
;;; την επανατοποθετούμε γεωαναφερμένη στις μετρικές συντεταγμένες ΕΓΣΑ87.
(if (null dgm:*wms-url*)
  (setq dgm:*wms-url* "http://gis.ktimanet.gr/wms/wmsopen/wmsserver.aspx"))
(if (null dgm:*wms-layer*) (setq dgm:*wms-layer* "BASEMAP"))
;; JPEG: χωρίς διαφάνεια (η ορθοφωτογραφία δεν βγαίνει μαύρη στο CAD)
(if (null dgm:*wms-fmt*)   (setq dgm:*wms-fmt* "image/jpeg"))

;; Κατάληξη αρχείου από το format
(defun dgm:fmt-ext (fmt)
  (cond ((wcmatch (strcase fmt) "*JPEG*,*JPG*") "jpg")
        ((wcmatch (strcase fmt) "*PNG*") "png")
        (t "img")))

;; --- Μετασχηματισμός ΕΓΣΑ87 (EPSG:2100) <-> WGS84 (EPSG:4326) ---
;; Ελλειψοειδές GRS80/WGS84 (πρακτικά ταυτόσημα), εγκάρσια Mercator με
;; κεντρικό μεσημβρινό 24°, k0=0.9996, FE=500000, FN=0. Μετάθεση datum
;; GGRS87 -> WGS84 (3 παράμετροι): dX=-199.87, dY=74.79, dZ=246.62 (m).
(setq dgm:*tm-a*    6378137.0)
(setq dgm:*tm-f*    (/ 1.0 298.257222101))
(setq dgm:*tm-e2*   (* dgm:*tm-f* (- 2.0 dgm:*tm-f*)))
(setq dgm:*tm-k0*   0.9996)
(setq dgm:*tm-fe*   500000.0)
(setq dgm:*tm-fn*   0.0)
(setq dgm:*tm-lon0* (/ (* 24.0 pi) 180.0))
(setq dgm:*dx*     -199.87)
(setq dgm:*dy*       74.79)
(setq dgm:*dz*      246.62)

;; Μήκος μεσημβρινού τόξου M(φ)
(defun dgm:tm-M (phi / e2 c1 c2 c3 c4)
  (setq e2 dgm:*tm-e2*)
  (setq c1 (- 1.0 (/ e2 4.0) (/ (* 3.0 e2 e2) 64.0) (/ (* 5.0 e2 e2 e2) 256.0)))
  (setq c2 (+ (/ (* 3.0 e2) 8.0) (/ (* 3.0 e2 e2) 32.0) (/ (* 45.0 e2 e2 e2) 1024.0)))
  (setq c3 (+ (/ (* 15.0 e2 e2) 256.0) (/ (* 45.0 e2 e2 e2) 1024.0)))
  (setq c4 (/ (* 35.0 e2 e2 e2) 3072.0))
  (* dgm:*tm-a*
     (+ (* c1 phi)
        (- (* c2 (sin (* 2.0 phi))))
        (* c3 (sin (* 4.0 phi)))
        (- (* c4 (sin (* 6.0 phi)))))))

;; Ευθεία TM: γεωγραφικές (φ,λ σε rad) -> προβολικές (E,N)
(defun dgm:tm-fwd (phi lam / e2 ep2 n tt c aa m sp cp)
  (setq e2 dgm:*tm-e2* ep2 (/ e2 (- 1.0 e2)))
  (setq sp (sin phi) cp (cos phi))
  (setq n (/ dgm:*tm-a* (sqrt (- 1.0 (* e2 sp sp)))))
  (setq tt (* (/ sp cp) (/ sp cp)))
  (setq c (* ep2 cp cp))
  (setq aa (* (- lam dgm:*tm-lon0*) cp))
  (setq m (dgm:tm-M phi))
  (list
    (+ dgm:*tm-fe*
       (* dgm:*tm-k0* n
          (+ aa
             (* (/ (expt aa 3) 6.0) (+ (- 1.0 tt) c))
             (* (/ (expt aa 5) 120.0)
                (+ 5.0 (* -18.0 tt) (* tt tt) (* 72.0 c) (* -58.0 ep2))))))
    (+ dgm:*tm-fn*
       (* dgm:*tm-k0*
          (+ m
             (* n (/ sp cp)
                (+ (/ (* aa aa) 2.0)
                   (* (/ (expt aa 4) 24.0)
                      (+ 5.0 (- tt) (* 9.0 c) (* 4.0 c c)))
                   (* (/ (expt aa 6) 720.0)
                      (+ 61.0 (* -58.0 tt) (* tt tt) (* 600.0 c) (* -330.0 ep2))))))))))

;; Αντίστροφη TM: προβολικές (E,N) -> γεωγραφικές (φ,λ σε rad)
(defun dgm:tm-inv (e n / e2 ep2 m mu e1 phi1 c1 t1 n1 r1 d sp cp phi lam)
  (setq e2 dgm:*tm-e2* ep2 (/ e2 (- 1.0 e2)))
  (setq m (/ (- n dgm:*tm-fn*) dgm:*tm-k0*))
  (setq mu (/ m (* dgm:*tm-a*
                   (- 1.0 (/ e2 4.0) (/ (* 3.0 e2 e2) 64.0)
                      (/ (* 5.0 e2 e2 e2) 256.0)))))
  (setq e1 (/ (- 1.0 (sqrt (- 1.0 e2))) (+ 1.0 (sqrt (- 1.0 e2)))))
  (setq phi1 (+ mu
                (* (- (/ (* 3.0 e1) 2.0) (/ (* 27.0 (expt e1 3)) 32.0))
                   (sin (* 2.0 mu)))
                (* (- (/ (* 21.0 e1 e1) 16.0) (/ (* 55.0 (expt e1 4)) 32.0))
                   (sin (* 4.0 mu)))
                (* (/ (* 151.0 (expt e1 3)) 96.0) (sin (* 6.0 mu)))
                (* (/ (* 1097.0 (expt e1 4)) 512.0) (sin (* 8.0 mu)))))
  (setq sp (sin phi1) cp (cos phi1))
  (setq c1 (* ep2 cp cp))
  (setq t1 (* (/ sp cp) (/ sp cp)))
  (setq n1 (/ dgm:*tm-a* (sqrt (- 1.0 (* e2 sp sp)))))
  (setq r1 (/ (* dgm:*tm-a* (- 1.0 e2)) (expt (- 1.0 (* e2 sp sp)) 1.5)))
  (setq d (/ (- e dgm:*tm-fe*) (* n1 dgm:*tm-k0*)))
  (setq phi (- phi1
               (* (/ (* n1 (/ sp cp)) r1)
                  (+ (/ (* d d) 2.0)
                     (- (* (/ (expt d 4) 24.0)
                           (+ 5.0 (* 3.0 t1) (* 10.0 c1) (* -4.0 c1 c1)
                              (* -9.0 ep2))))
                     (* (/ (expt d 6) 720.0)
                        (+ 61.0 (* 90.0 t1) (* 298.0 c1) (* 45.0 t1 t1)
                           (* -252.0 ep2) (* -3.0 c1 c1)))))))
  (setq lam (+ dgm:*tm-lon0*
               (/ (+ d
                     (- (* (/ (expt d 3) 6.0) (+ 1.0 (* 2.0 t1) c1)))
                     (* (/ (expt d 5) 120.0)
                        (+ 5.0 (* -2.0 c1) (* 28.0 t1) (* -3.0 c1 c1)
                           (* 8.0 ep2) (* 24.0 t1 t1))))
                  cp)))
  (list phi lam))

;; Γεωγραφικές (φ,λ rad) -> γεωκεντρικές (X,Y,Z), ύψος 0
(defun dgm:geo2xyz (phi lam / n sp cp)
  (setq sp (sin phi) cp (cos phi))
  (setq n (/ dgm:*tm-a* (sqrt (- 1.0 (* dgm:*tm-e2* sp sp)))))
  (list (* n cp (cos lam))
        (* n cp (sin lam))
        (* n (- 1.0 dgm:*tm-e2*) sp)))

;; Γεωκεντρικές (X,Y,Z) -> γεωγραφικές (φ,λ rad), επαναληπτικά
(defun dgm:xyz2geo (x y z / lam p phi i n sp)
  (setq lam (atan y x))
  (setq p (sqrt (+ (* x x) (* y y))))
  (setq phi (atan z (* p (- 1.0 dgm:*tm-e2*))))
  (setq i 0)
  (while (< i 8)
    (setq sp (sin phi))
    (setq n (/ dgm:*tm-a* (sqrt (- 1.0 (* dgm:*tm-e2* sp sp)))))
    (setq phi (atan (+ z (* dgm:*tm-e2* n sp)) p))
    (setq i (1+ i)))
  (list phi lam))

;; ΕΓΣΑ87 (E,N) -> WGS84 (lon,lat σε μοίρες)
(defun dgm:egsa->wgs (e n / pl xyz g)
  (setq pl (dgm:tm-inv e n))
  (setq xyz (dgm:geo2xyz (car pl) (cadr pl)))
  (setq xyz (list (+ (car xyz) dgm:*dx*)
                  (+ (cadr xyz) dgm:*dy*)
                  (+ (caddr xyz) dgm:*dz*)))
  (setq g (dgm:xyz2geo (car xyz) (cadr xyz) (caddr xyz)))
  (list (/ (* (cadr g) 180.0) pi)
        (/ (* (car g) 180.0) pi)))

;; WGS84 (lon,lat σε μοίρες) -> ΕΓΣΑ87 (E,N)
(defun dgm:wgs->egsa (lon lat / phi lam xyz g)
  (setq phi (/ (* lat pi) 180.0) lam (/ (* lon pi) 180.0))
  (setq xyz (dgm:geo2xyz phi lam))
  (setq xyz (list (- (car xyz) dgm:*dx*)
                  (- (cadr xyz) dgm:*dy*)
                  (- (caddr xyz) dgm:*dz*)))
  (setq g (dgm:xyz2geo (car xyz) (cadr xyz) (caddr xyz)))
  (dgm:tm-fwd (car g) (cadr g)))

;; Αληθές αν η συμβολοσειρά περιέχει μόνο χαρακτήρες ASCII (<128). Διαδρομές
;; με ελληνικούς χαρακτήρες δεν φορτώνονται από τον raster loader/COM όταν
;; περνούν ως συμβολοσειρά εντολής, γι' αυτό τις ανιχνεύουμε.
(defun dgm:asciip (s / i ok)
  (setq ok T i 0)
  (while (< i (strlen s))
    (if (> (ascii (substr s (1+ i) 1)) 127) (setq ok nil))
    (setq i (1+ i)))
  ok)

;; Φάκελος cache με ASCII διαδρομή (για εικόνες όταν το project path είναι
;; ελληνικό). Επιστρέφει τη διαδρομή (με \\ στο τέλος) ή nil.
(defun dgm:cache-dir ( / d r)
  (setq d "C:\\progecad_ortho\\")
  (vl-catch-all-apply
    '(lambda () (if (not (vl-file-directory-p d)) (vl-mkdir d))))
  (setq r (vl-catch-all-apply '(lambda () (vl-file-directory-p d))))
  (if (and (not (vl-catch-all-error-p r)) r) d nil))

;; Χρονοσφραγίδα ASCII από το CDATE (π.χ. 20260105_153245)
(defun dgm:stamp ( / c o i ch)
  (setq c (rtos (getvar "CDATE") 2 6) o "" i 0)
  (while (< i (strlen c))
    (setq ch (substr c (1+ i) 1))
    (setq o (strcat o (if (= ch ".") "_" ch)))
    (setq i (1+ i)))
  o)

;; Προσάρτηση raster γεωαναφερμένα. Επιστρέφει το entity της εικόνας ή nil.
;; pt=κάτω-αριστερά (ΕΓΣΑ87). Προσαρτά με κλίμακα 1.0· η σωστή κλίμακα
;; μπαίνει μετά με dgm:fit-image (η έννοια του scale factor διαφέρει ανά
;; έκδοση, γι' αυτό μετράμε το αποτέλεσμα αντί να τη μαντεύουμε).
(defun dgm:attach-image (file pt / prev fd last en acad doc ms ins img)
  ;; 1) Εντολή -IMAGE _Attach με FILEDIA=0 ώστε το όνομα αρχείου να διαβαστεί
  ;;    από τη γραμμή εντολών (όχι από διάλογο αρχείων).
  (setq prev (entlast) fd (getvar "FILEDIA"))
  (setvar "FILEDIA" 0)
  (vl-catch-all-apply
    '(lambda () (command "_.-IMAGE" "_Attach" file pt 1.0 0)))
  (if fd (setvar "FILEDIA" fd))
  (setq last (entlast))
  (if (and last (not (eq last prev))
           (= "IMAGE" (cdr (assoc 0 (entget last)))))
    (setq en last))
  ;; 2) Εφεδρική μέθοδος: ActiveX AddRaster (εντελώς χωρίς διάλογο).
  (if (null en)
    (progn
      (if vl-load-com (vl-load-com))
      (setq prev (entlast))
      (vl-catch-all-apply
        '(lambda ()
           (setq acad (vlax-get-acad-object)
                 doc  (vla-get-activedocument acad)
                 ms   (vla-get-modelspace doc)
                 ins  (vlax-3d-point (car pt) (cadr pt) 0.0)
                 img  (vla-addraster ms file ins 1.0 0.0))
           (setq en (vlax-vla-object->ename img))))
      ;; αν η επιστροφή απέτυχε αλλά δημιουργήθηκε οντότητα, υιοθέτησέ την
      (if (or (null en) (/= 'ENAME (type en)))
        (progn
          (setq en nil last (entlast))
          (if (and last (not (eq last prev))
                   (= "IMAGE" (cdr (assoc 0 (entget last)))))
            (setq en last))))))
  en)

;; Προσαρμογή κλίμακας: μετρά το πραγματικό πλάτος της εικόνας (από το U-vector
;; group 11 και το μέγεθος σε pixel group 13, ή μέσω bounding box) και την
;; κλιμακώνει ώστε το πλάτος να γίνει ακριβώς gw (m), με βάση το pt (κάτω-αρ).
(defun dgm:fit-image (en pt gw / d uvec sz curw factor obj lo hi)
  (setq d (entget en)
        uvec (cdr (assoc 11 d))
        sz   (cdr (assoc 13 d)))
  (if (and uvec sz)
    (setq curw (* (distance '(0.0 0.0 0.0) uvec) (car sz))))
  (if (or (null curw) (<= curw 1e-9))
    (vl-catch-all-apply
      '(lambda ()
         (if vl-load-com (vl-load-com))
         (setq obj (vlax-ename->vla-object en))
         (vla-getboundingbox obj 'lo 'hi)
         (setq curw (- (car (vlax-safearray->list hi))
                       (car (vlax-safearray->list lo)))))))
  (if (and curw (> curw 1e-9))
    (progn
      (setq factor (/ gw curw))
      (if (> (abs (- factor 1.0)) 1e-6)
        (command "_.SCALE" en "" (list (car pt) (cadr pt)) factor))))
  en)

;; Αφαίρεση κατάληξης αρχείου (ό,τι μετά την τελευταία τελεία)
(defun dgm:strip-ext (fn / i dot)
  (setq i (strlen fn) dot 0)
  (while (and (> i 0) (= dot 0))
    (if (= (substr fn i 1) ".") (setq dot i))
    (setq i (1- i)))
  (if (> dot 0) (substr fn 1 (1- dot)) fn))

;; Εγγραφή λιστών γραμμών σε αρχείο κειμένου
(defun dgm:writelines (fn lines / f)
  (if (setq f (open fn "w"))
    (progn (foreach l lines (write-line l f)) (close f) T)
    nil))

;; Δημιουργία world file (γεωαναφοράς) δίπλα στην εικόνα, ώστε η χειροκίνητη
;; εισαγωγή (IMAGEATTACH) να τοποθετεί την εικόνα αυτόματα στη σωστή θέση,
;; κλίμακα και χωρίς περιστροφή. plx,ply = κάτω-αριστερά (ΕΓΣΑ87),
;; gw,gh = διαστάσεις εδάφους (m), w,h = pixel, ext = κατάληξη εικόνας.
;; Σειρά γραμμών: A, D, B, E, C, F (A,E=μέγεθος pixel· C,F=κέντρο άνω-αρ pixel)
(defun dgm:make-worldfiles (file plx ply gw gh w h ext / base we ax ey cx fy lines)
  (setq base (dgm:strip-ext file)
        we   (if (= (strlen ext) 3)
                 (strcat (substr ext 1 1) (substr ext 3 1) "w")
                 "wld")
        ax (/ gw (float w))
        ey (- (/ gh (float h)))
        cx (+ plx (/ ax 2.0))
        fy (- (+ ply gh) (/ (/ gh (float h)) 2.0))
        lines (list (rtos ax 2 10) "0.0" "0.0"
                    (rtos ey 2 10) (rtos cx 2 6) (rtos fy 2 6)))
  (dgm:writelines (strcat base "." we) lines)
  (dgm:writelines (strcat base ".wld") lines)
  (strcat base "." we))

(defun c:DGMORTHO ( / items xmin ymin xmax ymax p marg res lyr w h f url file
                     cmd s ext ll lr ul ur lonmin lonmax latmin latmax
                     pll pur gw gh sb it imgen afile wf)
  (setq items (dgm:collect '("TOPO_PROP") nil))
  (if (null items)
    (princ "\n** Δεν βρέθηκε polyline στο layer TOPO_PROP. **")
    (progn
      ;; bbox όλων των κορυφών TOPO_PROP (σε ΕΓΣΑ87)
      (foreach it items
        (foreach p (cadr it)
          (if (null xmin)
            (setq xmin (car p) xmax (car p) ymin (cadr p) ymax (cadr p))
            (progn
              (if (< (car p) xmin) (setq xmin (car p)))
              (if (> (car p) xmax) (setq xmax (car p)))
              (if (< (cadr p) ymin) (setq ymin (cadr p)))
              (if (> (cadr p) ymax) (setq ymax (cadr p)))))))
      (setq marg (dgm:getreal "\nΠεριθώριο γύρω από το γεωτεμάχιο (m)" 10.0))
      (setq xmin (- xmin marg) ymin (- ymin marg)
            xmax (+ xmax marg) ymax (+ ymax marg))
      (setq res (dgm:getreal "\nΑνάλυση εδάφους (m/pixel)" 0.25))
      (if (<= res 0.0) (setq res 0.25))
      (setq lyr (dgm:getstr "\nΌνομα layer WMS" dgm:*wms-layer*))
      (setq dgm:*wms-layer* lyr)
      ;; Μετατροπή των 4 γωνιών του bbox ΕΓΣΑ87 -> WGS84 lon/lat και
      ;; υπολογισμός του γεωγραφικού bbox που περικλείει το γεωτεμάχιο.
      (setq ll (dgm:egsa->wgs xmin ymin)
            lr (dgm:egsa->wgs xmax ymin)
            ul (dgm:egsa->wgs xmin ymax)
            ur (dgm:egsa->wgs xmax ymax))
      (setq lonmin (min (car ll) (car lr) (car ul) (car ur))
            lonmax (max (car ll) (car lr) (car ul) (car ur))
            latmin (min (cadr ll) (cadr lr) (cadr ul) (cadr ur))
            latmax (max (cadr ll) (cadr lr) (cadr ul) (cadr ur)))
      ;; Μετρικό ορθογώνιο τοποθέτησης (επαναφορά του γεωγραφικού bbox σε ΕΓΣΑ87)
      (setq pll (dgm:wgs->egsa lonmin latmin)
            pur (dgm:wgs->egsa lonmax latmax))
      (setq gw (- (car pur) (car pll))
            gh (- (cadr pur) (cadr pll)))
      (setq w (fix (/ gw res)) h (fix (/ gh res)))
      (if (< w 1) (setq w 1))
      (if (< h 1) (setq h 1))
      ;; όριο μέγιστης διάστασης εικόνας WMS
      (if (> (max w h) 4000)
        (progn
          (setq f (/ 4000.0 (float (max w h))))
          (setq w (max 1 (fix (* w f))) h (max 1 (fix (* h f))))))
      ;; URL GetMap (WMS 1.1.0, EPSG:4326, BBOX = lonmin,latmin,lonmax,latmax)
      ;; TRANSPARENT=FALSE + λευκό φόντο: η no-data περιοχή γίνεται λευκή.
      (setq url (strcat dgm:*wms-url*
                        "?SERVICE=WMS&VERSION=1.1.0&REQUEST=GetMap&LAYERS="
                        lyr "&SRS=EPSG:4326&BBOX="
                        (rtos lonmin 2 8) "," (rtos latmin 2 8) ","
                        (rtos lonmax 2 8) "," (rtos latmax 2 8)
                        "&WIDTH=" (itoa w) "&HEIGHT=" (itoa h)
                        "&FORMAT=" dgm:*wms-fmt*
                        "&TRANSPARENT=FALSE&BGCOLOR=0xFFFFFF"
                        "&EXCEPTIONS=application/vnd.ogc.se_inimage&STYLES="))
      (setq ext (dgm:fmt-ext dgm:*wms-fmt*))
      (setq file (getfiled "Αποθήκευση ορθοφωτογραφίας" "ortho_topo" ext 1))
      (if file
        (progn
          (princ (strcat "\nΛήψη ορθοφωτογραφίας (" (itoa w) "x" (itoa h)
                         " px) από το Κτηματολόγιο..."))
          (setq cmd (strcat "cmd /c curl -s -L -o \"" file "\" \"" url "\""))
          (dgm:runsync cmd)
          (if (and (findfile file) (> (dgm:fsize file) 2000))
            (progn
              (dgm:layer "ORTHO" 8)
              (setvar "CLAYER" "ORTHO")
              ;; world file (γεωαναφορά) δίπλα στο jpg -> αυτόματη τοποθέτηση
              ;; κατά τη χειροκίνητη εισαγωγή (θέση, κλίμακα, χωρίς περιστροφή)
              (setq wf (dgm:make-worldfiles file (car pll) (cadr pll)
                                            gw gh w h ext))
              (setq imgen (dgm:attach-image file (list (car pll) (cadr pll))))
              ;; Αν η διαδρομή έχει ελληνικούς χαρακτήρες και η προσάρτηση
              ;; απέτυχε, κατέβασε αντίγραφο σε ASCII φάκελο (με world file)
              ;; και προσάρτησέ το από εκεί.
              (if (and (null imgen) (not (dgm:asciip file)) (dgm:cache-dir))
                (progn
                  (setq afile (strcat (dgm:cache-dir) "ortho_" (dgm:stamp)
                                      "." ext))
                  (dgm:runsync (strcat "cmd /c curl -s -L -o \"" afile
                                       "\" \"" url "\""))
                  (if (and (findfile afile) (> (dgm:fsize afile) 2000))
                    (progn
                      (dgm:make-worldfiles afile (car pll) (cadr pll)
                                           gw gh w h ext)
                      (setq imgen (dgm:attach-image afile
                                    (list (car pll) (cadr pll)))
                            file afile
                            wf (strcat (dgm:strip-ext afile) "."
                                       (if (= (strlen ext) 3)
                                         (strcat (substr ext 1 1)
                                                 (substr ext 3 1) "w")
                                         "wld")))))))
              (if imgen
                (progn
                  ;; διόρθωση κλίμακας ώστε το πλάτος να γίνει ακριβώς gw (m)
                  (dgm:fit-image imgen (list (car pll) (cadr pll)) gw)
                  ;; η εικόνα στο βάθος
                  (command "_.DRAWORDER" imgen "" "_Back")
                  ;; το περίγραμμα των polyline TOPO_PROP πάνω από την εικόνα
                  (setq sb (ssadd))
                  (foreach it items (ssadd (car it) sb))
                  (if (> (sslength sb) 0)
                    (command "_.DRAWORDER" sb "" "_Front"))
                  (princ (strcat "\nΕισήχθη η ορθοφωτογραφία γεωαναφερμένη ("
                                 (rtos gw 2 1) " x " (rtos gh 2 1)
                                 " m, ΕΓΣΑ87, layer ORTHO), με το περίγραμμα "
                                 "TOPO_PROP πάνω της.\nΑρχείο εικόνας: " file
                                 "\nWorld file: " wf
                                 "\nΑν υπάρχει μικρή ομοιόμορφη μετατόπιση "
                                 "(~10 m, όριο ακρίβειας datum), ευθυγραμμίστε "
                                 "με μία εντολή MOVE πάνω στο περίγραμμα "
                                 "TOPO_PROP.")))
                (princ (strcat "\n** Η εικόνα κατέβηκε αλλά ΔΕΝ προσαρτήθηκε "
                               "αυτόματα σε αυτή την έκδοση. Δημιουργήθηκε "
                               "world file δίπλα της:\n  Εικόνα: " file
                               "\n  World file: " wf
                               "\nΚάντε απλώς IMAGEATTACH και επιλέξτε την "
                               "εικόνα - θα τοποθετηθεί ΑΥΤΟΜΑΤΑ στη σωστή "
                               "θέση και κλίμακα (τυχόν μικρή μετατόπιση ~10 m "
                               "με μία MOVE στο περίγραμμα TOPO_PROP). **"))))
            (princ (strcat "\n** Η λήψη απέτυχε ή το αρχείο είναι κενό. "
                           "Ελέγξτε τη σύνδεση και το endpoint. **")))))))
  (princ))

;; Μέγεθος αρχείου σε bytes (0 αν δεν υπάρχει· 99999 αν δεν υποστηρίζεται)
(defun dgm:fsize (fn / r)
  (if (findfile fn)
    (progn
      (if vl-load-com (vl-load-com))
      (setq r (vl-catch-all-apply 'vl-file-size (list fn)))
      (if (vl-catch-all-error-p r) 99999 r))
    0))

;;; DGMORTHOCAP - Λήψη GetCapabilities του WMS (για έλεγχο ονομάτων layers)
(defun c:DGMORTHOCAP ( / url file cmd)
  (setq url (strcat dgm:*wms-url*
                    "?SERVICE=WMS&VERSION=1.1.1&REQUEST=GetCapabilities"))
  (setq file (getfiled "Αποθήκευση GetCapabilities" "wms_capabilities" "xml" 1))
  (if file
    (progn
      (princ "\nΛήψη GetCapabilities...")
      (setq cmd (strcat "cmd /c curl -s -L -o \"" file "\" \"" url "\""))
      (dgm:runsync cmd)
      (if (and (findfile file) (> (dgm:fsize file) 200))
        (progn
          (princ (strcat "\nΑποθηκεύτηκε: " file
                         "  (δείτε τα <Layer><Name> για το σωστό layer)."))
          (startapp "notepad.exe" file))
        (princ "\n** Αποτυχία λήψης GetCapabilities. **"))))
  (princ))

;;; DGMHELP - Βοήθεια
(defun c:DGMHELP ()
  (princ "\n----------------- Εντολές GF-DGM -----------------")
  (princ "\nΠροετοιμασία:")
  (princ "\n  DGML      Δημιουργία layers ανά τύπο διαγράμματος")
  (princ "\n  DGMSCALE  Κλίμακα σχεδίασης (1:100 ως 1:2000)")
  (princ "\n  DGMGRID   Κάναβος σχεδίασης + σύμβολο βορρά")
  (princ "\n  DGMSHEET  Κάναβος-φύλλο 609mm x κλίμακα, μήκος για όλο το σχέδιο")
  (princ "\n  DGMORTHO  Απόσπασμα ορθοφωτοχάρτη TOPO_PROP (Κτηματολόγιο, layer BASEMAP)")
  (princ "\n  DGMORTHOCAP Λήψη λίστας WMS layers (GetCapabilities)")
  (princ "\n  DGMCLEAN  Αυτόματος καθαρισμός τυπικών σφαλμάτων")
  (princ "\n  DGMC      Έλεγχος ορθότητας σχεδίου")
  (princ "\n  DGMNEAR   Σχεδόν-συμπίπτουσες κορυφές ΔΓΜ (ζώνη 0.0004-0.005 m)")
  (princ "\nΣύντομη ροή ΔΓΜ:  DGML -> σχεδίαση -> DGMOUR -> DGMGEO -> DGMC -> DGMAUTO -> παράδοση")
  (princ "\n  DGMOUR    Επιλογή της polyline DGM_PROP_FINAL του δικού μας γεωτεμαχίου")
  (princ "\n  DGMGEO    Γεωμετρία σε ένα βήμα: DGM_PROP_FINAL επηρεαζόμενων ομόρων + AREA_A/AREA_D")
  (princ "\nΠολύγωνα:")
  (princ "\n  DGMBND    Πολύγωνο από εσωτερικό σημείο")
  (princ "\n  DGMBNDPD  Πολύγωνο από σημείο (μόνο PST_KAEK/DGM_PROP_FINAL)")
  (princ "\n  DGMKAT    DGM_PROP_FINAL: κατάτμηση PST_KAEK με LINE_XM")
  (princ "\n  DGMGM     DGM_PROP_FINAL των επηρεαζόμενων ομόρων (ως προς το δικό μας, DGMOUR)")
  (princ "\n  DGMVST    VST_FINAL από LINE_XM_VST")
  (princ "\n  DGMAREAS  Αυτόματη δημιουργία AREA_A / AREA_D")
  (princ "\n  DGMSKETCH Σκαρίφημα Αρχικών (καφέ) / Τελικών (μπλε) ΚΑΕΚ, solid hatch")
  (princ "\n  DGMSPLIT  Κατάτμηση πολυγώνου με γραμμή κοπής")
  (princ "\n  DGMUNION  Συνένωση όμορων πολυγώνων")
  (princ "\n  DGMCUT    Αποκοπή τμήματος από γεωτεμάχιο")
  (princ "\n  DGMA      Χειροκίνητος χαρακτηρισμός τμήματος Α/Δ")
  (princ "\n  DGMCOPY   Αντιγραφή TOPO_PROP σε άλλα layers")
  (princ "\nΑρίθμηση - Πίνακες:")
  (princ "\n  DGMK      Μαζική αρίθμηση κορυφών + προαιρετικές διαστάσεις πλευρών")
  (princ "\n  DGMORIGIN Αλλαγή αρχής/φοράς κλειστής polyline")
  (princ "\n  DGMP      Πίνακας συντεταγμένων κορυφών (μία polyline)")
  (princ "\n  DGMPALL   Πίνακες για όλες τις polylines αυτόματα (layer + ΚΑΕΚ)")
  (princ "\n  DGMTA     Πίνακες τμημάτων Αi (AREA_A) και Δi (AREA_D)")
  (princ "\n  DGMAUTO   Αρίθμηση + ΟΛΟΙ οι πίνακες αυτόματα (συντεταγμένων, εμβαδών, διόρθωσης, Αi/Δi)")
  (princ "\nΣημείωση: κάθε εντολή αναιρείται συνολικά με ένα U/UNDO.")
  (princ "\n  DGME      Πίνακας αρχικών/τελικών εμβαδών")
  (princ "\n  DGMT      Πίνακας για τη διόρθωση των γεωτεμαχίων")
  (princ "\n  DGMTXT    Εξαγωγή συντεταγμένων σε TXT")
  (princ "\nΠαραδοτέα:")
  (princ "\n  DGMPREP   Προετοιμασία σχεδίου (images/blocks/OLE/xrefs)")
  (princ "\n  DGMHASH   Hash SHA512 αρχείου DXF")
  (princ "\n  DGMKHD    Τοποθέτηση ΚΗΔ στο σχέδιο")
  (princ "\n  DGMSIGN   Υπογραφή PDF με JSignPdf")
  (princ "\n  DGMZIP    ZIP παραδοτέων (DXF + υπογεγραμμένο PDF)")
  (princ "\n---------------------------------------------------")
  (princ))

;;; ==================== ΟΜΑΔΟΠΟΙΗΣΗ UNDO ================================
;;; Κάθε εντολή τυλίγεται σε UNDO Begin/End ώστε ένα U/UNDO να αναιρεί
;;; συνολικά όλες τις αλλαγές της τελευταίας εντολής.

(defun dgm:runwrapped (osym / *error*)
  (defun *error* (msg)
    (setq dgm:*auto* nil)
    (command "_.UNDO" "_E")
    (if (and msg
             (/= msg "Function cancelled")
             (/= msg "quit / exit abort"))
      (princ (strcat "\nΣφάλμα: " msg)))
    (princ))
  (setq dgm:*auto* nil)
  (command "_.UNDO" "_BE")
  (apply (eval osym) nil)
  (command "_.UNDO" "_E")
  (princ))

(defun dgm:wrapcmd (nm / csym osym)
  (setq csym (read (strcat "C:" nm))
        osym (read (strcat "DGM:ORIG-" nm)))
  (if (and (eval csym) (null (eval osym)))
    (progn
      (set osym (eval csym))
      (eval (list 'defun csym '()
                  (list 'dgm:runwrapped (list 'quote osym)))))))

(foreach dgm:tmp '("DGML" "DGMK" "DGMP" "DGMPALL" "DGMTA" "DGMNEAR" "DGMAUTO" "DGME" "DGMT"
                   "DGMA" "DGMKAEK" "DGMKHD" "DGMC" "DGMCLEAN" "DGMORIGIN"
                   "DGMBND" "DGMBNDPD" "DGMKAT" "DGMVST" "DGMGM" "DGMAREAS" "DGMGEO" "DGMOUR"
                   "DGMCOPY" "DGMSPLIT" "DGMUNION" "DGMCUT" "DGMGRID"
                   "DGMSHEET" "DGMORTHO" "DGMORTHOCAP" "DGMSKETCH" "DGMPREP")
  (dgm:wrapcmd dgm:tmp))
(setq dgm:tmp nil)

(princ "\nDGM.lsp: Φορτώθηκαν τα εργαλεία ΔΓΜ. Πληκτρολογήστε DGMHELP για λίστα εντολών.")
(princ)
